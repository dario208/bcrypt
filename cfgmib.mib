COMAP-InteliNeo5500-43 DEFINITIONS ::= BEGIN

--******************************************************************--
IMPORTS
    OBJECT-GROUP, NOTIFICATION-GROUP
        FROM SNMPv2-CONF
    Gauge32, Integer32, OBJECT-TYPE, MODULE-IDENTITY, NOTIFICATION-TYPE, enterprises
        FROM SNMPv2-SMI
    DisplayString
        FROM SNMPv2-TC;

ineo5500-43 MODULE-IDENTITY
LAST-UPDATED "202502050806Z"
ORGANIZATION "ComAp a.s."
CONTACT-INFO "ComAp"
DESCRIPTION  "InteliNeo5500-43"
REVISION     "202502050806Z"
DESCRIPTION  "None"
::= {enterprises 28634 43}

--******************************************************************--

notifications		OBJECT IDENTIFIER ::= { ineo5500-43 0 }
groupRdFix			OBJECT IDENTIFIER ::= { ineo5500-43 1 }
groupRdCfg			OBJECT IDENTIFIER ::= { ineo5500-43 2 }
groupWrFix			OBJECT IDENTIFIER ::= { ineo5500-43 3 }
groupWrCfg			OBJECT IDENTIFIER ::= { ineo5500-43 4 }
groupW				OBJECT IDENTIFIER ::= { ineo5500-43 5 }
notificationData	OBJECT IDENTIFIER ::= { ineo5500-43 6 }
conformanceGroups	OBJECT IDENTIFIER ::= { ineo5500-43 10}

--******************************************************************--


--******************************************************************--

conformanceGroupRdCfg OBJECT-GROUP
	OBJECTS { vBESSVoltageL1N, vBESSVoltageL2N, vBESSVoltageL3N, vMainsCHR2FBusVoltageL1N, vMainsCHR2FBusVoltageL2N,
vMainsCHR2FBusVoltageL3N, vBESSCurrentL1, vBESSCurrentL2, vBESSCurrentL3, vBESSP,
vBESSQ, vBESSPowerFactor, vPCCKWh, vRunningHours, vNumStarts,
vBESSFrequency, vMainsCHR2FBusFrequency, vBatteryVolts, vBinaryInputs, vBinaryOutputs,
vBESSLoadCharacter, vBESSPL1, vBESSPL2, vBESSPL3, vBESSQL1,
vBESSQL2, vBESSQL3, vBESSSL1, vBESSSL2, vBESSSL3,
vBESSPowerFactorL1, vBESSPowerFactorL2, vBESSPowerFactorL3, vPCCKVArh, vBESSS,
vBESSLoadCharacterL1, vBESSLoadCharacterL2, vBESSLoadCharacterL3, vBESSRequiredPTarget, vMainsImportP,
vMainsImportQ, vMainsPF, vMainsLoadCharacter, vMainsPL1, vMainsPL2,
vMainsPL3, vMainsQL1, vMainsQL2, vMainsQL3, vMainsS,
vMainsSL1, vMainsSL2, vMainsSL3, vMainsLoadCharacterL1, vMainsLoadCharacterL2,
vMainsLoadCharacterL3, vFrequencyRegulatorOutput, vVoltageRegulatorOutput, vCUAIN01, vCUAIN02,
vCUAIN03, vNotUsed, vBESSVoltageL1L2, vBESSVoltageL2L3, vBESSVoltageL3L1,
vMainsCHR2FBusVoltageL1L2, vMainsCHR2FBusVoltageL2L3, vMainsCHR2FBusVoltageL3L1, vControllerMode, vVoltageMatch321,
vCUTemperature, vDPlus, vSystemLoadControl, vMainsKWh, vMainsKVArh,
vNumEStops, vShutdowns, vMaintenanceTimer1RunHours, vMaintenanceTimer2RunHours, vMaintenanceTimer3RunHours,
vMaintenanceTimer4RunHours, vBESSRequiredQ, vBESSRequiredP, vBESSRequiredQrelLim, vPCCKVAh,
vCurtailmentOutput, vEarthFaultCurrent, vVoltageRequest, vPVKWh, vPVAnnualKWh,
vPVMonthlyKWh, vPVWeeklyKWh, vPVDailyKWh, vGenKWh, vGenAnnualKWh,
vGenMonthlyKWh, vGenWeeklyKWh, vGenDailyKWh, vFuelUsed, vFuelAnnual,
vFuelMonthly, vFuelWeekly, vFuelDaily, vPVActualP, vPVActualQ,
vPVNominalP, vPVActualLoadCharacter, vBattCHR2EChargeKWh, vBattCHR2EChargeAnnualKWh, vBattCHR2EChargeMonthKWh,
vBattCHR2EChargeWeekKWh, vBattCHR2EChargeDailyKWh, vBattCHR2EDischargeKWh, vBattCHR2EDischargeAnnualKWh, vBattCHR2EDischargeMonthKWh,
vBattCHR2EDischargeWeekKWh, vBattCHR2EDischargeDailyKWh, vWTKWh, vWTAnnualKWh, vWTMonthlyKWh,
vWTWeeklyKWh, vWTDailyKWh, vBESSSOC, vBESSNominalCapacity, vBESSTemperature,
vPVActualS, vBESSRequiredRelativeP, vBESSRequiredRelativeQ, vBESSVoltageTHDL1, vBESSVoltageTHDL2,
vBESSVoltageTHDL3, vBESSCurrentTHDL1, vBESSCurrentTHDL2, vBESSCurrentTHDL3, vMainsVoltageTHDL1,
vMainsVoltageTHDL2, vMainsVoltageTHDL3, vMainsCurrentTHDL1, vMainsCurrentTHDL2, vMainsCurrentTHDL3,
vBESSP10minAvg, vBESSQ10minAvg, vBESSS10minAvg, vBESSPowerFactor, vMainsPF,
vBESSRequiredPF, vBESSPowerFactorL1, vBESSPowerFactorL2, vBESSPowerFactorL3, vPlusMainsCHR2FBusVoltage,
vPlusMainsCHR2FBusVoltageRelative, vTotalCurtailedPVKWhRel, vAnnualCurtailedPVKWhRel, vMonthlyCurtailedPVKWhRel, vWeeklyCurtailedPVKWhRel,
vDailyCurtailedPVKWhRel, vUniGen1ActualS, vUniGen2ActualS, vUniGen3ActualS, vUniGen4ActualS,
vUniGen1ActualQ, vUniGen2ActualQ, vUniGen3ActualQ, vUniGen4ActualQ, vUniGen1ActualP,
vUniGen2ActualP, vUniGen3ActualP, vUniGen4ActualP, vUniGenRequestedP, vUniGen1RequestedQ,
vUniGen2RequestedQ, vUniGen3RequestedQ, vUniGen4RequestedQ, vUniGen1RequestedP, vUniGen2RequestedP,
vUniGen3RequestedP, vUniGen4RequestedP, vUniGenActualLoadCharacter, vUniGenActualPowerFactor, vUniGenActualS,
vUniGenActualQ, vUniGenActualP, vUniGenNominalP, vUniGen1ActualLoadCharacter, vUniGen2ActualLoadCharacter,
vUniGen3ActualLoadCharacter, vUniGen4ActualLoadCharacter, vUniGen1ActualPowerFactor, vUniGen2ActualPowerFactor, vUniGen3ActualPowerFactor,
vUniGen4ActualPowerFactor, vUniGenRelativeRequestedQ, vUniGenRelativeRequestedP, vUniGenRequestedQ, vUniGen1NominalP,
vUniGen2NominalP, vUniGen3NominalP, vUniGen4NominalP, vECUAIN32288, vECUAIN32287,
vECUAIN32286, vECUAIN32285, vECUAIN32284, vECUAIN32283, vECUAIN32282,
vECUAIN32281, vECUAIN32280, vECUAIN32279, vECUAIN32278, vECUAIN32277,
vECUAIN32276, vECUAIN32275, vECUAIN32274, vECUAIN32273, vECUAIN32272,
vECUAIN32271, vECUAIN32270, vECUAIN32269, vECUAIN32268, vECUAIN32267,
vECUAIN32266, vECUAIN32265, vECUAIN32264, vECUAIN32263, vECUAIN32262,
vECUAIN32261, vECUAIN32260, vECUAIN32259, vECUAIN32258, vECUAIN32257,
vECUAIN32256, vECUAIN32255, vECUAIN32254, vECUAIN32253, vECUAIN32252,
vECUAIN32251, vECUAIN32250, vECUAIN32249, vECUAIN32248, vECUAIN32247,
vECUAIN32246, vECUAIN32245, vECUAIN32244, vECUAIN32243, vECUAIN32242,
vECUAIN32241, vECUAIN32240, vECUAIN32239, vECUAIN32238, vECUAIN32237,
vECUAIN32236, vECUAIN32235, vECUAIN32234, vECUAIN32233, vECUAIN32232,
vECUAIN32231, vECUAIN32230, vECUAIN32229, vECUAIN32228, vECUAIN32227,
vECUAIN32226, vECUAIN32225, vECUAIN32224, vECUAIN32223, vECUAIN32222,
vECUAIN32221, vECUAIN32220, vECUAIN32219, vECUAIN32218, vECUAIN32217,
vECUAIN32216, vECUAIN32215, vECUAIN32214, vECUAIN32213, vECUAIN32212,
vECUAIN32211, vECUAIN32210, vECUAIN32209, vECUAIN32208, vECUAIN32207,
vECUAIN32206, vECUAIN32205, vECUAIN32204, vECUAIN32203, vECUAIN32202,
vECUAIN32201, vECUAIN32200, vECUAIN32199, vECUAIN32198, vECUAIN32197,
vECUAIN32196, vECUAIN32195, vECUAIN32194, vECUAIN32193, vECUAIN32192,
vECUAIN32191, vECUAIN32190, vECUAIN32189, vECUAIN32188, vECUAIN32187,
vECUAIN32186, vECUAIN32185, vECUAIN32184, vECUAIN32183, vECUAIN32182,
vECUAIN32181, vECUAIN32180, vECUAIN32179, vECUAIN32178, vECUAIN32177,
vECUAIN32176, vECUAIN32175, vECUAIN32174, vECUAIN32173, vECUAIN32172,
vECUAIN32171, vECUAIN32170, vECUAIN32169, vECUAIN32168, vECUAIN32167,
vECUAIN32166, vECUAIN32165, vECUAIN32164, vECUAIN32163, vECUAIN32162,
vECUAIN32161, vECUAIN32160, vECUAIN32159, vECUAIN32158, vECUAIN32157,
vECUAIN32156, vECUAIN32155, vECUAIN32154, vECUAIN32153, vECUAIN32152,
vECUAIN32151, vECUAIN32150, vECUAIN32149, vECUAIN32148, vECUAIN32147,
vECUAIN32146, vECUAIN32145, vECUAIN32144, vECUAIN32143, vECUAIN32142,
vECUAIN32141, vECUAIN32140, vECUAIN32139, vECUAIN32138, vECUAIN32137,
vECUAIN32136, vECUAIN32135, vECUAIN32134, vECUAIN32133, vECUAIN32132,
vECUAIN32131, vECUAIN32130, vECUAIN32129, vECUAIN32128, vECUAIN32127,
vECUAIN32126, vECUAIN32125, vECUAIN32124, vECUAIN32123, vECUAIN32122,
vECUAIN32121, vECUAIN32120, vECUAIN32119, vECUAIN32118, vECUAIN32117,
vECUAIN32116, vECUAIN32115, vECUAIN32114, vECUAIN32113, vECUAIN32112,
vECUAIN32111, vECUAIN32110, vECUAIN32109, vECUAIN32108, vECUAIN32107,
vECUAIN32106, vECUAIN32105, vECUAIN32104, vECUAIN32103, vECUAIN32102,
vECUAIN32101, vECUAIN32100, vECUAIN3299, vECUAIN3298, vECUAIN3297,
vECUAIN3296, vECUAIN3295, vECUAIN3294, vECUAIN3293, vECUAIN3292,
vECUAIN3291, vECUAIN3290, vECUAIN3289, vECUAIN3288, vECUAIN3287,
vECUAIN3286, vECUAIN3285, vECUAIN3284, vECUAIN3283, vECUAIN3282,
vECUAIN3281, vECUAIN3280, vECUAIN3279, vECUAIN3278, vECUAIN3277,
vECUAIN3276, vECUAIN3275, vECUAIN3274, vECUAIN3273, vECUAIN3272,
vECUAIN3271, vECUAIN3270, vECUAIN3269, vECUAIN3268, vECUAIN3267,
vECUAIN3266, vECUAIN3265, vECUAIN3264, vECUAIN3263, vECUAIN3262,
vECUAIN3261, vECUAIN3260, vECUAIN3259, vECUAIN3258, vECUAIN3257,
vECUAIN3256, vECUAIN3255, vECUAIN3254, vECUAIN3253, vECUAIN3252,
vECUAIN3251, vECUAIN3250, vECUAIN3249, vECUAIN3248, vECUAIN3247,
vECUAIN3246, vECUAIN3245, vECUAIN3244, vECUAIN3243, vECUAIN3242,
vECUAIN3241, vECUAIN3240, vECUAIN3239, vECUAIN3238, vECUAIN3237,
vReactivePower, vECUAIN3235, vGridFrequency, vGridVoltageL3L1, vGridVoltageL2L3,
vGridVoltageL1L2, vActivePower, vECUAIN3229, vCurrentL3, vCurrentL2,
vCurrentL1, vECUAIN3225, vSOH, vSOC, vECUAIN3222,
vECUAIN3221, vReleasedEnergy, vAbsorbedEnergy, vACTNRJEXPORT, vACTNRJIMPORT,
vREACTPOWER, vREACTPercent, vACTPOWER, vTOTKWhPV1, vTOTKWhPV2,
vPFSET, vREACTPercent, vRealTimeActivePowerPercent, vReactivePower, vActivePower,
vInputPower, vMaximumApparentPower, vMaximumActivePower, vNominalActivePower, vReactivePower,
vActivePower, vBESSVoltageRequired, vBESSVoltageOffset, vBESSQRequiredPercent, vBESSFrequencyRequired,
vBESSFrequencyOffset, vBESSPRequired, vPVTotalCurtailedKWh, vPVCurtailedAnnualKWh, vPVCurtailedMonthlyKWh,
vPVCurtailedWeeklyKWh, vPVCurtailedDailyKWh, vPVMaxP, vPVCurtailedP, vPVCurtailedPRelative,
vExerciseTimer1, vExerciseTimer2, vExerciseTimer3, vExerciseTimer4, vExerciseTimer5,
vExerciseTimer6, vRENActualLoadCharacter, vRENActualPowerFactor, vRENActualS, vRENActualQ,
vRENActualP, vRENNominalP, vWTActualLoadCharacter, vWTActualPowerFactor, vWTActualS,
vWTActualQ, vWTActualP, vWTNominalP, vWT2ActualLoadCharacter, vWT2ActualPowerFactor,
vWT2ActualS, vWT2ActualQ, vWT2ActualP, vWT2NominalP, vWT1ActualLoadCharacter,
vWT1ActualPowerFactor, vWT1ActualS, vWT1ActualQ, vWT1ActualP, vWT1NominalP,
vPV8ActualLoadCharacter, vPV8ActualPowerFactor, vPV8ActualS, vPV8ActualQ, vPV8ActualP,
vPV8NominalP, vPV7ActualLoadCharacter, vPV7ActualPowerFactor, vPV7ActualS, vPV7ActualQ,
vPV7ActualP, vPV7NominalP, vPV6ActualLoadCharacter, vPV6ActualPowerFactor, vPV6ActualS,
vPV6ActualQ, vPV6ActualP, vPV6NominalP, vPV5ActualLoadCharacter, vPV5ActualPowerFactor,
vPV5ActualS, vPV5ActualQ, vPV5ActualP, vPV5NominalP, vPV4ActualLoadCharacter,
vPV4ActualPowerFactor, vPV4ActualS, vPV4ActualQ, vPV4ActualP, vPV4NominalP,
vPV3ActualLoadCharacter, vPV3ActualPowerFactor, vPV3ActualS, vPV3ActualQ, vPV3ActualP,
vPV3NominalP, vPV2ActualLoadCharacter, vPV2ActualPowerFactor, vPV2ActualS, vPV2ActualQ,
vPV2ActualP, vPV2NominalP, vPV1ActualLoadCharacter, vPV1ActualPowerFactor, vPV1ActualS,
vPV1ActualQ, vPV1ActualP, vPV1NominalP, v3PhCTLocation, vCarbonOffsetEquivalent,
vHoursOfSilent, vPVActualPowerFactor, vTotalLoadCharacter, vTotalPF, vTotalS,
vTotalQ, vTotalP, vMainsImportQMonitoring, vMainsImportPMonitoring, vGensetsLoadCharacter,
vGensetsPowerFactor, vGensetsQ, vGensetsP, vBattCHR2EChargingCycles, vMainsPowerFactorL1,
vBESSFrequency, vMainsCHR2FBusFrequency, vDate, vTime }
	STATUS  current
	DESCRIPTION  "Objects for reading only"
	::= { conformanceGroups 1 }

vBESSVoltageL1N	OBJECT-TYPE
	SYNTAX	Integer32(0..65535)
	MAX-ACCESS	read-only
	STATUS	current
	DESCRIPTION	"DEC=0, UNIT='V'"
 ::= { groupRdCfg 8192 }

vBESSVoltageL2N	OBJECT-TYPE
	SYNTAX	Integer32(0..65535)
	MAX-ACCESS	read-only
	STATUS	current
	DESCRIPTION	"DEC=0, UNIT='V'"
 ::= { groupRdCfg 8193 }

vBESSVoltageL3N	OBJECT-TYPE
	SYNTAX	Integer32(0..65535)
	MAX-ACCESS	read-only
	STATUS	current
	DESCRIPTION	"DEC=0, UNIT='V'"
 ::= { groupRdCfg 8194 }

vMainsCHR2FBusVoltageL1N	OBJECT-TYPE
	SYNTAX	Integer32(0..65535)
	MAX-ACCESS	read-only
	STATUS	current
	DESCRIPTION	"DEC=0, UNIT='V'"
 ::= { groupRdCfg 8195 }

vMainsCHR2FBusVoltageL2N	OBJECT-TYPE
	SYNTAX	Integer32(0..65535)
	MAX-ACCESS	read-only
	STATUS	current
	DESCRIPTION	"DEC=0, UNIT='V'"
 ::= { groupRdCfg 8196 }

vMainsCHR2FBusVoltageL3N	OBJECT-TYPE
	SYNTAX	Integer32(0..65535)
	MAX-ACCESS	read-only
	STATUS	current
	DESCRIPTION	"DEC=0, UNIT='V'"
 ::= { groupRdCfg 8197 }

vBESSCurrentL1	OBJECT-TYPE
	SYNTAX	Integer32(0..65535)
	MAX-ACCESS	read-only
	STATUS	current
	DESCRIPTION	"DEC=0, UNIT='A'"
 ::= { groupRdCfg 8198 }

vBESSCurrentL2	OBJECT-TYPE
	SYNTAX	Integer32(0..65535)
	MAX-ACCESS	read-only
	STATUS	current
	DESCRIPTION	"DEC=0, UNIT='A'"
 ::= { groupRdCfg 8199 }

vBESSCurrentL3	OBJECT-TYPE
	SYNTAX	Integer32(0..65535)
	MAX-ACCESS	read-only
	STATUS	current
	DESCRIPTION	"DEC=0, UNIT='A'"
 ::= { groupRdCfg 8200 }

vBESSP	OBJECT-TYPE
	SYNTAX	Integer32(-32768..32767)
	MAX-ACCESS	read-only
	STATUS	current
	DESCRIPTION	"DEC=0, UNIT='kW'"
 ::= { groupRdCfg 8202 }

vBESSQ	OBJECT-TYPE
	SYNTAX	Integer32(-32768..32767)
	MAX-ACCESS	read-only
	STATUS	current
	DESCRIPTION	"DEC=0, UNIT='kVAr'"
 ::= { groupRdCfg 8203 }

vBESSPowerFactor	OBJECT-TYPE
	SYNTAX	Integer32(-128..127)
	MAX-ACCESS	read-only
	STATUS	current
	DESCRIPTION	"DEC=2, UNIT=''"
 ::= { groupRdCfg 8204 }

vPCCKWh	OBJECT-TYPE
	SYNTAX	Integer32
	MAX-ACCESS	read-only
	STATUS	current
	DESCRIPTION	"DEC=0, UNIT='kWh'"
 ::= { groupRdCfg 8205 }

vRunningHours	OBJECT-TYPE
	SYNTAX	Integer32
	MAX-ACCESS	read-only
	STATUS	current
	DESCRIPTION	"DEC=1, UNIT='h'"
 ::= { groupRdCfg 8206 }

vNumStarts	OBJECT-TYPE
	SYNTAX	Integer32(0..65535)
	MAX-ACCESS	read-only
	STATUS	current
	DESCRIPTION	"DEC=0, UNIT=''"
 ::= { groupRdCfg 8207 }

vBESSFrequency	OBJECT-TYPE
	SYNTAX	Integer32(0..65535)
	MAX-ACCESS	read-only
	STATUS	current
	DESCRIPTION	"DEC=1, UNIT='Hz'"
 ::= { groupRdCfg 8210 }

vMainsCHR2FBusFrequency	OBJECT-TYPE
	SYNTAX	Integer32(0..65535)
	MAX-ACCESS	read-only
	STATUS	current
	DESCRIPTION	"DEC=1, UNIT='Hz'"
 ::= { groupRdCfg 8211 }

vBatteryVolts	OBJECT-TYPE
	SYNTAX	Integer32(-32768..32767)
	MAX-ACCESS	read-only
	STATUS	current
	DESCRIPTION	"DEC=1, UNIT='V'"
 ::= { groupRdCfg 8213 }

vBinaryInputs	OBJECT-TYPE
	SYNTAX	OCTET STRING
	MAX-ACCESS	read-only
	STATUS	current
	DESCRIPTION	"BINARY, BITS=8"
 ::= { groupRdCfg 8235 }

vBinaryOutputs	OBJECT-TYPE
	SYNTAX	OCTET STRING
	MAX-ACCESS	read-only
	STATUS	current
	DESCRIPTION	"BINARY, BITS=8"
 ::= { groupRdCfg 8239 }

vBESSLoadCharacter	OBJECT-TYPE
	SYNTAX	DisplayString
	MAX-ACCESS	read-only
	STATUS	current
	DESCRIPTION	"String"
 ::= { groupRdCfg 8395 }

vBESSPL1	OBJECT-TYPE
	SYNTAX	Integer32(-32768..32767)
	MAX-ACCESS	read-only
	STATUS	current
	DESCRIPTION	"DEC=0, UNIT='kW'"
 ::= { groupRdCfg 8524 }

vBESSPL2	OBJECT-TYPE
	SYNTAX	Integer32(-32768..32767)
	MAX-ACCESS	read-only
	STATUS	current
	DESCRIPTION	"DEC=0, UNIT='kW'"
 ::= { groupRdCfg 8525 }

vBESSPL3	OBJECT-TYPE
	SYNTAX	Integer32(-32768..32767)
	MAX-ACCESS	read-only
	STATUS	current
	DESCRIPTION	"DEC=0, UNIT='kW'"
 ::= { groupRdCfg 8526 }

vBESSQL1	OBJECT-TYPE
	SYNTAX	Integer32(-32768..32767)
	MAX-ACCESS	read-only
	STATUS	current
	DESCRIPTION	"DEC=0, UNIT='kVAr'"
 ::= { groupRdCfg 8527 }

vBESSQL2	OBJECT-TYPE
	SYNTAX	Integer32(-32768..32767)
	MAX-ACCESS	read-only
	STATUS	current
	DESCRIPTION	"DEC=0, UNIT='kVAr'"
 ::= { groupRdCfg 8528 }

vBESSQL3	OBJECT-TYPE
	SYNTAX	Integer32(-32768..32767)
	MAX-ACCESS	read-only
	STATUS	current
	DESCRIPTION	"DEC=0, UNIT='kVAr'"
 ::= { groupRdCfg 8529 }

vBESSSL1	OBJECT-TYPE
	SYNTAX	Integer32(-32768..32767)
	MAX-ACCESS	read-only
	STATUS	current
	DESCRIPTION	"DEC=0, UNIT='kVA'"
 ::= { groupRdCfg 8530 }

vBESSSL2	OBJECT-TYPE
	SYNTAX	Integer32(-32768..32767)
	MAX-ACCESS	read-only
	STATUS	current
	DESCRIPTION	"DEC=0, UNIT='kVA'"
 ::= { groupRdCfg 8531 }

vBESSSL3	OBJECT-TYPE
	SYNTAX	Integer32(-32768..32767)
	MAX-ACCESS	read-only
	STATUS	current
	DESCRIPTION	"DEC=0, UNIT='kVA'"
 ::= { groupRdCfg 8532 }

vBESSPowerFactorL1	OBJECT-TYPE
	SYNTAX	Integer32(-128..127)
	MAX-ACCESS	read-only
	STATUS	current
	DESCRIPTION	"DEC=2, UNIT=''"
 ::= { groupRdCfg 8533 }

vBESSPowerFactorL2	OBJECT-TYPE
	SYNTAX	Integer32(-128..127)
	MAX-ACCESS	read-only
	STATUS	current
	DESCRIPTION	"DEC=2, UNIT=''"
 ::= { groupRdCfg 8534 }

vBESSPowerFactorL3	OBJECT-TYPE
	SYNTAX	Integer32(-128..127)
	MAX-ACCESS	read-only
	STATUS	current
	DESCRIPTION	"DEC=2, UNIT=''"
 ::= { groupRdCfg 8535 }

vPCCKVArh	OBJECT-TYPE
	SYNTAX	Integer32
	MAX-ACCESS	read-only
	STATUS	current
	DESCRIPTION	"DEC=0, UNIT='kVArh'"
 ::= { groupRdCfg 8539 }

vBESSS	OBJECT-TYPE
	SYNTAX	Integer32(-32768..32767)
	MAX-ACCESS	read-only
	STATUS	current
	DESCRIPTION	"DEC=0, UNIT='kVA'"
 ::= { groupRdCfg 8565 }

vBESSLoadCharacterL1	OBJECT-TYPE
	SYNTAX	DisplayString
	MAX-ACCESS	read-only
	STATUS	current
	DESCRIPTION	"String"
 ::= { groupRdCfg 8626 }

vBESSLoadCharacterL2	OBJECT-TYPE
	SYNTAX	DisplayString
	MAX-ACCESS	read-only
	STATUS	current
	DESCRIPTION	"String"
 ::= { groupRdCfg 8627 }

vBESSLoadCharacterL3	OBJECT-TYPE
	SYNTAX	DisplayString
	MAX-ACCESS	read-only
	STATUS	current
	DESCRIPTION	"String"
 ::= { groupRdCfg 8628 }

vBESSRequiredPTarget	OBJECT-TYPE
	SYNTAX	Integer32(-32768..32767)
	MAX-ACCESS	read-only
	STATUS	current
	DESCRIPTION	"DEC=0, UNIT='kW'"
 ::= { groupRdCfg 8663 }

vMainsImportP	OBJECT-TYPE
	SYNTAX	Integer32(-32768..32767)
	MAX-ACCESS	read-only
	STATUS	current
	DESCRIPTION	"DEC=0, UNIT='kW'"
 ::= { groupRdCfg 8703 }

vMainsImportQ	OBJECT-TYPE
	SYNTAX	Integer32(-32768..32767)
	MAX-ACCESS	read-only
	STATUS	current
	DESCRIPTION	"DEC=0, UNIT='kVAr'"
 ::= { groupRdCfg 8704 }

vMainsPF	OBJECT-TYPE
	SYNTAX	Integer32(-128..127)
	MAX-ACCESS	read-only
	STATUS	current
	DESCRIPTION	"DEC=2, UNIT=''"
 ::= { groupRdCfg 8705 }

vMainsLoadCharacter	OBJECT-TYPE
	SYNTAX	DisplayString
	MAX-ACCESS	read-only
	STATUS	current
	DESCRIPTION	"String"
 ::= { groupRdCfg 8709 }

vMainsPL1	OBJECT-TYPE
	SYNTAX	Integer32(-32768..32767)
	MAX-ACCESS	read-only
	STATUS	current
	DESCRIPTION	"DEC=0, UNIT='kW'"
 ::= { groupRdCfg 8805 }

vMainsPL2	OBJECT-TYPE
	SYNTAX	Integer32(-32768..32767)
	MAX-ACCESS	read-only
	STATUS	current
	DESCRIPTION	"DEC=0, UNIT='kW'"
 ::= { groupRdCfg 8806 }

vMainsPL3	OBJECT-TYPE
	SYNTAX	Integer32(-32768..32767)
	MAX-ACCESS	read-only
	STATUS	current
	DESCRIPTION	"DEC=0, UNIT='kW'"
 ::= { groupRdCfg 8807 }

vMainsQL1	OBJECT-TYPE
	SYNTAX	Integer32(-32768..32767)
	MAX-ACCESS	read-only
	STATUS	current
	DESCRIPTION	"DEC=0, UNIT='kVAr'"
 ::= { groupRdCfg 8808 }

vMainsQL2	OBJECT-TYPE
	SYNTAX	Integer32(-32768..32767)
	MAX-ACCESS	read-only
	STATUS	current
	DESCRIPTION	"DEC=0, UNIT='kVAr'"
 ::= { groupRdCfg 8809 }

vMainsQL3	OBJECT-TYPE
	SYNTAX	Integer32(-32768..32767)
	MAX-ACCESS	read-only
	STATUS	current
	DESCRIPTION	"DEC=0, UNIT='kVAr'"
 ::= { groupRdCfg 8810 }

vMainsS	OBJECT-TYPE
	SYNTAX	Integer32(-32768..32767)
	MAX-ACCESS	read-only
	STATUS	current
	DESCRIPTION	"DEC=0, UNIT='kVA'"
 ::= { groupRdCfg 8811 }

vMainsSL1	OBJECT-TYPE
	SYNTAX	Integer32(-32768..32767)
	MAX-ACCESS	read-only
	STATUS	current
	DESCRIPTION	"DEC=0, UNIT='kVA'"
 ::= { groupRdCfg 8812 }

vMainsSL2	OBJECT-TYPE
	SYNTAX	Integer32(-32768..32767)
	MAX-ACCESS	read-only
	STATUS	current
	DESCRIPTION	"DEC=0, UNIT='kVA'"
 ::= { groupRdCfg 8813 }

vMainsSL3	OBJECT-TYPE
	SYNTAX	Integer32(-32768..32767)
	MAX-ACCESS	read-only
	STATUS	current
	DESCRIPTION	"DEC=0, UNIT='kVA'"
 ::= { groupRdCfg 8814 }

vMainsLoadCharacterL1	OBJECT-TYPE
	SYNTAX	DisplayString
	MAX-ACCESS	read-only
	STATUS	current
	DESCRIPTION	"String"
 ::= { groupRdCfg 8818 }

vMainsLoadCharacterL2	OBJECT-TYPE
	SYNTAX	DisplayString
	MAX-ACCESS	read-only
	STATUS	current
	DESCRIPTION	"String"
 ::= { groupRdCfg 8819 }

vMainsLoadCharacterL3	OBJECT-TYPE
	SYNTAX	DisplayString
	MAX-ACCESS	read-only
	STATUS	current
	DESCRIPTION	"String"
 ::= { groupRdCfg 8820 }

vFrequencyRegulatorOutput	OBJECT-TYPE
	SYNTAX	Integer32(-32768..32767)
	MAX-ACCESS	read-only
	STATUS	current
	DESCRIPTION	"DEC=3, UNIT='V'"
 ::= { groupRdCfg 9052 }

vVoltageRegulatorOutput	OBJECT-TYPE
	SYNTAX	Integer32(-32768..32767)
	MAX-ACCESS	read-only
	STATUS	current
	DESCRIPTION	"DEC=3, UNIT='V'"
 ::= { groupRdCfg 9053 }

vCUAIN01	OBJECT-TYPE
	SYNTAX	Integer32(-32768..32767)
	MAX-ACCESS	read-only
	STATUS	current
	DESCRIPTION	"DEC=1, UNIT='A'"
 ::= { groupRdCfg 9151 }

vCUAIN02	OBJECT-TYPE
	SYNTAX	Integer32(-32768..32767)
	MAX-ACCESS	read-only
	STATUS	current
	DESCRIPTION	"DEC=0, UNIT=''"
 ::= { groupRdCfg 9152 }

vCUAIN03	OBJECT-TYPE
	SYNTAX	Integer32(-32768..32767)
	MAX-ACCESS	read-only
	STATUS	current
	DESCRIPTION	"DEC=0, UNIT=''"
 ::= { groupRdCfg 9153 }

vNotUsed	OBJECT-TYPE
	SYNTAX	Integer32(-32768..32767)
	MAX-ACCESS	read-only
	STATUS	current
	DESCRIPTION	"DEC=0, UNIT=''"
 ::= { groupRdCfg 9154 }

vBESSVoltageL1L2	OBJECT-TYPE
	SYNTAX	Integer32(0..65535)
	MAX-ACCESS	read-only
	STATUS	current
	DESCRIPTION	"DEC=0, UNIT='V'"
 ::= { groupRdCfg 9628 }

vBESSVoltageL2L3	OBJECT-TYPE
	SYNTAX	Integer32(0..65535)
	MAX-ACCESS	read-only
	STATUS	current
	DESCRIPTION	"DEC=0, UNIT='V'"
 ::= { groupRdCfg 9629 }

vBESSVoltageL3L1	OBJECT-TYPE
	SYNTAX	Integer32(0..65535)
	MAX-ACCESS	read-only
	STATUS	current
	DESCRIPTION	"DEC=0, UNIT='V'"
 ::= { groupRdCfg 9630 }

vMainsCHR2FBusVoltageL1L2	OBJECT-TYPE
	SYNTAX	Integer32(0..65535)
	MAX-ACCESS	read-only
	STATUS	current
	DESCRIPTION	"DEC=0, UNIT='V'"
 ::= { groupRdCfg 9631 }

vMainsCHR2FBusVoltageL2L3	OBJECT-TYPE
	SYNTAX	Integer32(0..65535)
	MAX-ACCESS	read-only
	STATUS	current
	DESCRIPTION	"DEC=0, UNIT='V'"
 ::= { groupRdCfg 9632 }

vMainsCHR2FBusVoltageL3L1	OBJECT-TYPE
	SYNTAX	Integer32(0..65535)
	MAX-ACCESS	read-only
	STATUS	current
	DESCRIPTION	"DEC=0, UNIT='V'"
 ::= { groupRdCfg 9633 }

vControllerMode	OBJECT-TYPE
	SYNTAX	Integer32(0..255)
	MAX-ACCESS	read-only
	STATUS	current
	DESCRIPTION	"LIST, 0-OFF, 1-MAN, 2-AUTO, 3-TEST"
 ::= { groupRdCfg 9887 }

vVoltageMatch321	OBJECT-TYPE
	SYNTAX	OCTET STRING
	MAX-ACCESS	read-only
	STATUS	current
	DESCRIPTION	"BINARY, BITS=8"
 ::= { groupRdCfg 9889 }

vCUTemperature	OBJECT-TYPE
	SYNTAX	Integer32(-32768..32767)
	MAX-ACCESS	read-only
	STATUS	current
	DESCRIPTION	"DEC=1, UNIT='DegreeC'"
 ::= { groupRdCfg 10124 }

vDPlus	OBJECT-TYPE
	SYNTAX	Integer32(-32768..32767)
	MAX-ACCESS	read-only
	STATUS	current
	DESCRIPTION	"DEC=1, UNIT='V'"
 ::= { groupRdCfg 10603 }

vSystemLoadControl	OBJECT-TYPE
	SYNTAX	Integer32(0..255)
	MAX-ACCESS	read-only
	STATUS	current
	DESCRIPTION	"LIST, 0-None, 1-Island, 2-Baseload, 3-BaseloadWithICHR2FELimit, 4-ImportCHR2FExport"
 ::= { groupRdCfg 10792 }

vMainsKWh	OBJECT-TYPE
	SYNTAX	Integer32
	MAX-ACCESS	read-only
	STATUS	current
	DESCRIPTION	"DEC=0, UNIT='kWh'"
 ::= { groupRdCfg 11025 }

vMainsKVArh	OBJECT-TYPE
	SYNTAX	Integer32
	MAX-ACCESS	read-only
	STATUS	current
	DESCRIPTION	"DEC=0, UNIT='kVArh'"
 ::= { groupRdCfg 11026 }

vNumEStops	OBJECT-TYPE
	SYNTAX	Gauge32
	MAX-ACCESS	read-only
	STATUS	current
	DESCRIPTION	"DEC=0, UNIT=''"
 ::= { groupRdCfg 11195 }

vShutdowns	OBJECT-TYPE
	SYNTAX	Gauge32
	MAX-ACCESS	read-only
	STATUS	current
	DESCRIPTION	"DEC=0, UNIT=''"
 ::= { groupRdCfg 11196 }

vMaintenanceTimer1RunHours	OBJECT-TYPE
	SYNTAX	Integer32(-32768..32767)
	MAX-ACCESS	read-only
	STATUS	current
	DESCRIPTION	"DEC=0, UNIT='h'"
 ::= { groupRdCfg 11616 }

vMaintenanceTimer2RunHours	OBJECT-TYPE
	SYNTAX	Integer32(-32768..32767)
	MAX-ACCESS	read-only
	STATUS	current
	DESCRIPTION	"DEC=0, UNIT='h'"
 ::= { groupRdCfg 11617 }

vMaintenanceTimer3RunHours	OBJECT-TYPE
	SYNTAX	Integer32(-32768..32767)
	MAX-ACCESS	read-only
	STATUS	current
	DESCRIPTION	"DEC=0, UNIT='h'"
 ::= { groupRdCfg 11618 }

vMaintenanceTimer4RunHours	OBJECT-TYPE
	SYNTAX	Integer32(-32768..32767)
	MAX-ACCESS	read-only
	STATUS	current
	DESCRIPTION	"DEC=0, UNIT='h'"
 ::= { groupRdCfg 11619 }

vBESSRequiredQ	OBJECT-TYPE
	SYNTAX	Integer32(-32768..32767)
	MAX-ACCESS	read-only
	STATUS	current
	DESCRIPTION	"DEC=0, UNIT='kVAr'"
 ::= { groupRdCfg 12877 }

vBESSRequiredP	OBJECT-TYPE
	SYNTAX	Integer32(-32768..32767)
	MAX-ACCESS	read-only
	STATUS	current
	DESCRIPTION	"DEC=0, UNIT='kW'"
 ::= { groupRdCfg 13105 }

vBESSRequiredQrelLim	OBJECT-TYPE
	SYNTAX	Integer32(-32768..32767)
	MAX-ACCESS	read-only
	STATUS	current
	DESCRIPTION	"DEC=0, UNIT='Percent'"
 ::= { groupRdCfg 13169 }

vPCCKVAh	OBJECT-TYPE
	SYNTAX	Integer32
	MAX-ACCESS	read-only
	STATUS	current
	DESCRIPTION	"DEC=0, UNIT='kVAh'"
 ::= { groupRdCfg 13663 }

vCurtailmentOutput	OBJECT-TYPE
	SYNTAX	Integer32(-32768..32767)
	MAX-ACCESS	read-only
	STATUS	current
	DESCRIPTION	"DEC=2, UNIT='Percent'"
 ::= { groupRdCfg 14364 }

vEarthFaultCurrent	OBJECT-TYPE
	SYNTAX	Integer32(0..65535)
	MAX-ACCESS	read-only
	STATUS	current
	DESCRIPTION	"DEC=0, UNIT='A'"
 ::= { groupRdCfg 14996 }

vVoltageRequest	OBJECT-TYPE
	SYNTAX	Integer32(-32768..32767)
	MAX-ACCESS	read-only
	STATUS	current
	DESCRIPTION	"DEC=1, UNIT='Percent'"
 ::= { groupRdCfg 14997 }

vPVKWh	OBJECT-TYPE
	SYNTAX	Gauge32
	MAX-ACCESS	read-only
	STATUS	current
	DESCRIPTION	"DEC=0, UNIT='kWh'"
 ::= { groupRdCfg 15575 }

vPVAnnualKWh	OBJECT-TYPE
	SYNTAX	Gauge32
	MAX-ACCESS	read-only
	STATUS	current
	DESCRIPTION	"DEC=0, UNIT='kWh'"
 ::= { groupRdCfg 15576 }

vPVMonthlyKWh	OBJECT-TYPE
	SYNTAX	Gauge32
	MAX-ACCESS	read-only
	STATUS	current
	DESCRIPTION	"DEC=0, UNIT='kWh'"
 ::= { groupRdCfg 15577 }

vPVWeeklyKWh	OBJECT-TYPE
	SYNTAX	Gauge32
	MAX-ACCESS	read-only
	STATUS	current
	DESCRIPTION	"DEC=0, UNIT='kWh'"
 ::= { groupRdCfg 15578 }

vPVDailyKWh	OBJECT-TYPE
	SYNTAX	Gauge32
	MAX-ACCESS	read-only
	STATUS	current
	DESCRIPTION	"DEC=0, UNIT='kWh'"
 ::= { groupRdCfg 15579 }

vGenKWh	OBJECT-TYPE
	SYNTAX	Gauge32
	MAX-ACCESS	read-only
	STATUS	current
	DESCRIPTION	"DEC=0, UNIT='kWh'"
 ::= { groupRdCfg 15580 }

vGenAnnualKWh	OBJECT-TYPE
	SYNTAX	Gauge32
	MAX-ACCESS	read-only
	STATUS	current
	DESCRIPTION	"DEC=0, UNIT='kWh'"
 ::= { groupRdCfg 15581 }

vGenMonthlyKWh	OBJECT-TYPE
	SYNTAX	Gauge32
	MAX-ACCESS	read-only
	STATUS	current
	DESCRIPTION	"DEC=0, UNIT='kWh'"
 ::= { groupRdCfg 15582 }

vGenWeeklyKWh	OBJECT-TYPE
	SYNTAX	Gauge32
	MAX-ACCESS	read-only
	STATUS	current
	DESCRIPTION	"DEC=0, UNIT='kWh'"
 ::= { groupRdCfg 15583 }

vGenDailyKWh	OBJECT-TYPE
	SYNTAX	Gauge32
	MAX-ACCESS	read-only
	STATUS	current
	DESCRIPTION	"DEC=0, UNIT='kWh'"
 ::= { groupRdCfg 15584 }

vFuelUsed	OBJECT-TYPE
	SYNTAX	Gauge32
	MAX-ACCESS	read-only
	STATUS	current
	DESCRIPTION	"DEC=0, UNIT='l'"
 ::= { groupRdCfg 15585 }

vFuelAnnual	OBJECT-TYPE
	SYNTAX	Gauge32
	MAX-ACCESS	read-only
	STATUS	current
	DESCRIPTION	"DEC=0, UNIT='l'"
 ::= { groupRdCfg 15586 }

vFuelMonthly	OBJECT-TYPE
	SYNTAX	Gauge32
	MAX-ACCESS	read-only
	STATUS	current
	DESCRIPTION	"DEC=0, UNIT='l'"
 ::= { groupRdCfg 15587 }

vFuelWeekly	OBJECT-TYPE
	SYNTAX	Gauge32
	MAX-ACCESS	read-only
	STATUS	current
	DESCRIPTION	"DEC=0, UNIT='l'"
 ::= { groupRdCfg 15588 }

vFuelDaily	OBJECT-TYPE
	SYNTAX	Gauge32
	MAX-ACCESS	read-only
	STATUS	current
	DESCRIPTION	"DEC=0, UNIT='l'"
 ::= { groupRdCfg 15589 }

vPVActualP	OBJECT-TYPE
	SYNTAX	Integer32(-32768..32767)
	MAX-ACCESS	read-only
	STATUS	current
	DESCRIPTION	"DEC=0, UNIT='kW'"
 ::= { groupRdCfg 15594 }

vPVActualQ	OBJECT-TYPE
	SYNTAX	Integer32(-32768..32767)
	MAX-ACCESS	read-only
	STATUS	current
	DESCRIPTION	"DEC=0, UNIT='kVAr'"
 ::= { groupRdCfg 15595 }

vPVNominalP	OBJECT-TYPE
	SYNTAX	Integer32(0..65535)
	MAX-ACCESS	read-only
	STATUS	current
	DESCRIPTION	"DEC=0, UNIT='kW'"
 ::= { groupRdCfg 15596 }

vPVActualLoadCharacter	OBJECT-TYPE
	SYNTAX	DisplayString
	MAX-ACCESS	read-only
	STATUS	current
	DESCRIPTION	"String"
 ::= { groupRdCfg 15678 }

vBattCHR2EChargeKWh	OBJECT-TYPE
	SYNTAX	Gauge32
	MAX-ACCESS	read-only
	STATUS	current
	DESCRIPTION	"DEC=0, UNIT='kWh'"
 ::= { groupRdCfg 15824 }

vBattCHR2EChargeAnnualKWh	OBJECT-TYPE
	SYNTAX	Gauge32
	MAX-ACCESS	read-only
	STATUS	current
	DESCRIPTION	"DEC=0, UNIT='kWh'"
 ::= { groupRdCfg 15825 }

vBattCHR2EChargeMonthKWh	OBJECT-TYPE
	SYNTAX	Gauge32
	MAX-ACCESS	read-only
	STATUS	current
	DESCRIPTION	"DEC=0, UNIT='kWh'"
 ::= { groupRdCfg 15826 }

vBattCHR2EChargeWeekKWh	OBJECT-TYPE
	SYNTAX	Gauge32
	MAX-ACCESS	read-only
	STATUS	current
	DESCRIPTION	"DEC=0, UNIT='kWh'"
 ::= { groupRdCfg 15827 }

vBattCHR2EChargeDailyKWh	OBJECT-TYPE
	SYNTAX	Gauge32
	MAX-ACCESS	read-only
	STATUS	current
	DESCRIPTION	"DEC=0, UNIT='kWh'"
 ::= { groupRdCfg 15828 }

vBattCHR2EDischargeKWh	OBJECT-TYPE
	SYNTAX	Gauge32
	MAX-ACCESS	read-only
	STATUS	current
	DESCRIPTION	"DEC=0, UNIT='kWh'"
 ::= { groupRdCfg 15829 }

vBattCHR2EDischargeAnnualKWh	OBJECT-TYPE
	SYNTAX	Gauge32
	MAX-ACCESS	read-only
	STATUS	current
	DESCRIPTION	"DEC=0, UNIT='kWh'"
 ::= { groupRdCfg 15830 }

vBattCHR2EDischargeMonthKWh	OBJECT-TYPE
	SYNTAX	Gauge32
	MAX-ACCESS	read-only
	STATUS	current
	DESCRIPTION	"DEC=0, UNIT='kWh'"
 ::= { groupRdCfg 15831 }

vBattCHR2EDischargeWeekKWh	OBJECT-TYPE
	SYNTAX	Gauge32
	MAX-ACCESS	read-only
	STATUS	current
	DESCRIPTION	"DEC=0, UNIT='kWh'"
 ::= { groupRdCfg 15832 }

vBattCHR2EDischargeDailyKWh	OBJECT-TYPE
	SYNTAX	Gauge32
	MAX-ACCESS	read-only
	STATUS	current
	DESCRIPTION	"DEC=0, UNIT='kWh'"
 ::= { groupRdCfg 15833 }

vWTKWh	OBJECT-TYPE
	SYNTAX	Gauge32
	MAX-ACCESS	read-only
	STATUS	current
	DESCRIPTION	"DEC=0, UNIT='kWh'"
 ::= { groupRdCfg 15834 }

vWTAnnualKWh	OBJECT-TYPE
	SYNTAX	Gauge32
	MAX-ACCESS	read-only
	STATUS	current
	DESCRIPTION	"DEC=0, UNIT='kWh'"
 ::= { groupRdCfg 15835 }

vWTMonthlyKWh	OBJECT-TYPE
	SYNTAX	Gauge32
	MAX-ACCESS	read-only
	STATUS	current
	DESCRIPTION	"DEC=0, UNIT='kWh'"
 ::= { groupRdCfg 15836 }

vWTWeeklyKWh	OBJECT-TYPE
	SYNTAX	Gauge32
	MAX-ACCESS	read-only
	STATUS	current
	DESCRIPTION	"DEC=0, UNIT='kWh'"
 ::= { groupRdCfg 15837 }

vWTDailyKWh	OBJECT-TYPE
	SYNTAX	Gauge32
	MAX-ACCESS	read-only
	STATUS	current
	DESCRIPTION	"DEC=0, UNIT='kWh'"
 ::= { groupRdCfg 15838 }

vBESSSOC	OBJECT-TYPE
	SYNTAX	Integer32(0..255)
	MAX-ACCESS	read-only
	STATUS	current
	DESCRIPTION	"DEC=0, UNIT='Percent'"
 ::= { groupRdCfg 15857 }

vBESSNominalCapacity	OBJECT-TYPE
	SYNTAX	Integer32(0..65535)
	MAX-ACCESS	read-only
	STATUS	current
	DESCRIPTION	"DEC=0, UNIT='kWh'"
 ::= { groupRdCfg 15859 }

vBESSTemperature	OBJECT-TYPE
	SYNTAX	Integer32(-32768..32767)
	MAX-ACCESS	read-only
	STATUS	current
	DESCRIPTION	"DEC=0, UNIT='DegreeC'"
 ::= { groupRdCfg 15861 }

vPVActualS	OBJECT-TYPE
	SYNTAX	Integer32(-32768..32767)
	MAX-ACCESS	read-only
	STATUS	current
	DESCRIPTION	"DEC=0, UNIT='kVA'"
 ::= { groupRdCfg 15891 }

vBESSRequiredRelativeP	OBJECT-TYPE
	SYNTAX	Integer32(-32768..32767)
	MAX-ACCESS	read-only
	STATUS	current
	DESCRIPTION	"DEC=2, UNIT='Percent'"
 ::= { groupRdCfg 15900 }

vBESSRequiredRelativeQ	OBJECT-TYPE
	SYNTAX	Integer32(-32768..32767)
	MAX-ACCESS	read-only
	STATUS	current
	DESCRIPTION	"DEC=2, UNIT='Percent'"
 ::= { groupRdCfg 15901 }

vBESSVoltageTHDL1	OBJECT-TYPE
	SYNTAX	Integer32(0..65535)
	MAX-ACCESS	read-only
	STATUS	current
	DESCRIPTION	"DEC=1, UNIT='Percent'"
 ::= { groupRdCfg 16052 }

vBESSVoltageTHDL2	OBJECT-TYPE
	SYNTAX	Integer32(0..65535)
	MAX-ACCESS	read-only
	STATUS	current
	DESCRIPTION	"DEC=1, UNIT='Percent'"
 ::= { groupRdCfg 16053 }

vBESSVoltageTHDL3	OBJECT-TYPE
	SYNTAX	Integer32(0..65535)
	MAX-ACCESS	read-only
	STATUS	current
	DESCRIPTION	"DEC=1, UNIT='Percent'"
 ::= { groupRdCfg 16054 }

vBESSCurrentTHDL1	OBJECT-TYPE
	SYNTAX	Integer32(0..65535)
	MAX-ACCESS	read-only
	STATUS	current
	DESCRIPTION	"DEC=1, UNIT='Percent'"
 ::= { groupRdCfg 16056 }

vBESSCurrentTHDL2	OBJECT-TYPE
	SYNTAX	Integer32(0..65535)
	MAX-ACCESS	read-only
	STATUS	current
	DESCRIPTION	"DEC=1, UNIT='Percent'"
 ::= { groupRdCfg 16057 }

vBESSCurrentTHDL3	OBJECT-TYPE
	SYNTAX	Integer32(0..65535)
	MAX-ACCESS	read-only
	STATUS	current
	DESCRIPTION	"DEC=1, UNIT='Percent'"
 ::= { groupRdCfg 16058 }

vMainsVoltageTHDL1	OBJECT-TYPE
	SYNTAX	Integer32(0..65535)
	MAX-ACCESS	read-only
	STATUS	current
	DESCRIPTION	"DEC=1, UNIT='Percent'"
 ::= { groupRdCfg 16060 }

vMainsVoltageTHDL2	OBJECT-TYPE
	SYNTAX	Integer32(0..65535)
	MAX-ACCESS	read-only
	STATUS	current
	DESCRIPTION	"DEC=1, UNIT='Percent'"
 ::= { groupRdCfg 16061 }

vMainsVoltageTHDL3	OBJECT-TYPE
	SYNTAX	Integer32(0..65535)
	MAX-ACCESS	read-only
	STATUS	current
	DESCRIPTION	"DEC=1, UNIT='Percent'"
 ::= { groupRdCfg 16062 }

vMainsCurrentTHDL1	OBJECT-TYPE
	SYNTAX	Integer32(0..65535)
	MAX-ACCESS	read-only
	STATUS	current
	DESCRIPTION	"DEC=1, UNIT='Percent'"
 ::= { groupRdCfg 16064 }

vMainsCurrentTHDL2	OBJECT-TYPE
	SYNTAX	Integer32(0..65535)
	MAX-ACCESS	read-only
	STATUS	current
	DESCRIPTION	"DEC=1, UNIT='Percent'"
 ::= { groupRdCfg 16065 }

vMainsCurrentTHDL3	OBJECT-TYPE
	SYNTAX	Integer32(0..65535)
	MAX-ACCESS	read-only
	STATUS	current
	DESCRIPTION	"DEC=1, UNIT='Percent'"
 ::= { groupRdCfg 16066 }

vBESSP10minAvg	OBJECT-TYPE
	SYNTAX	Integer32(-32768..32767)
	MAX-ACCESS	read-only
	STATUS	current
	DESCRIPTION	"DEC=0, UNIT='kW'"
 ::= { groupRdCfg 16073 }

vBESSQ10minAvg	OBJECT-TYPE
	SYNTAX	Integer32(-32768..32767)
	MAX-ACCESS	read-only
	STATUS	current
	DESCRIPTION	"DEC=0, UNIT='kVAr'"
 ::= { groupRdCfg 16080 }

vBESSS10minAvg	OBJECT-TYPE
	SYNTAX	Integer32(-32768..32767)
	MAX-ACCESS	read-only
	STATUS	current
	DESCRIPTION	"DEC=0, UNIT='kVA'"
 ::= { groupRdCfg 16081 }

vBESSPowerFactor	OBJECT-TYPE
	SYNTAX	Integer32(-32768..32767)
	MAX-ACCESS	read-only
	STATUS	current
	DESCRIPTION	"DEC=3, UNIT=''"
 ::= { groupRdCfg 16156 }

vMainsPF	OBJECT-TYPE
	SYNTAX	Integer32(-32768..32767)
	MAX-ACCESS	read-only
	STATUS	current
	DESCRIPTION	"DEC=3, UNIT=''"
 ::= { groupRdCfg 16157 }

vBESSRequiredPF	OBJECT-TYPE
	SYNTAX	Integer32(-32768..32767)
	MAX-ACCESS	read-only
	STATUS	current
	DESCRIPTION	"DEC=3, UNIT=''"
 ::= { groupRdCfg 16159 }

vBESSPowerFactorL1	OBJECT-TYPE
	SYNTAX	Integer32(-32768..32767)
	MAX-ACCESS	read-only
	STATUS	current
	DESCRIPTION	"DEC=3, UNIT=''"
 ::= { groupRdCfg 16160 }

vBESSPowerFactorL2	OBJECT-TYPE
	SYNTAX	Integer32(-32768..32767)
	MAX-ACCESS	read-only
	STATUS	current
	DESCRIPTION	"DEC=3, UNIT=''"
 ::= { groupRdCfg 16161 }

vBESSPowerFactorL3	OBJECT-TYPE
	SYNTAX	Integer32(-32768..32767)
	MAX-ACCESS	read-only
	STATUS	current
	DESCRIPTION	"DEC=3, UNIT=''"
 ::= { groupRdCfg 16162 }

vPlusMainsCHR2FBusVoltage	OBJECT-TYPE
	SYNTAX	Integer32(0..65535)
	MAX-ACCESS	read-only
	STATUS	current
	DESCRIPTION	"DEC=0, UNIT='V'"
 ::= { groupRdCfg 16615 }

vPlusMainsCHR2FBusVoltageRelative	OBJECT-TYPE
	SYNTAX	Integer32(-32768..32767)
	MAX-ACCESS	read-only
	STATUS	current
	DESCRIPTION	"DEC=2, UNIT='Percent'"
 ::= { groupRdCfg 16616 }

vTotalCurtailedPVKWhRel	OBJECT-TYPE
	SYNTAX	Gauge32
	MAX-ACCESS	read-only
	STATUS	current
	DESCRIPTION	"DEC=0, UNIT='Percent'"
 ::= { groupRdCfg 18711 }

vAnnualCurtailedPVKWhRel	OBJECT-TYPE
	SYNTAX	Gauge32
	MAX-ACCESS	read-only
	STATUS	current
	DESCRIPTION	"DEC=0, UNIT='Percent'"
 ::= { groupRdCfg 18712 }

vMonthlyCurtailedPVKWhRel	OBJECT-TYPE
	SYNTAX	Gauge32
	MAX-ACCESS	read-only
	STATUS	current
	DESCRIPTION	"DEC=0, UNIT='Percent'"
 ::= { groupRdCfg 18713 }

vWeeklyCurtailedPVKWhRel	OBJECT-TYPE
	SYNTAX	Gauge32
	MAX-ACCESS	read-only
	STATUS	current
	DESCRIPTION	"DEC=0, UNIT='Percent'"
 ::= { groupRdCfg 18714 }

vDailyCurtailedPVKWhRel	OBJECT-TYPE
	SYNTAX	Gauge32
	MAX-ACCESS	read-only
	STATUS	current
	DESCRIPTION	"DEC=0, UNIT='Percent'"
 ::= { groupRdCfg 18715 }

vUniGen1ActualS	OBJECT-TYPE
	SYNTAX	Integer32(-32768..32767)
	MAX-ACCESS	read-only
	STATUS	current
	DESCRIPTION	"DEC=0, UNIT='kVA'"
 ::= { groupRdCfg 18817 }

vUniGen2ActualS	OBJECT-TYPE
	SYNTAX	Integer32(-32768..32767)
	MAX-ACCESS	read-only
	STATUS	current
	DESCRIPTION	"DEC=0, UNIT='kVA'"
 ::= { groupRdCfg 18818 }

vUniGen3ActualS	OBJECT-TYPE
	SYNTAX	Integer32(-32768..32767)
	MAX-ACCESS	read-only
	STATUS	current
	DESCRIPTION	"DEC=0, UNIT='kVA'"
 ::= { groupRdCfg 18819 }

vUniGen4ActualS	OBJECT-TYPE
	SYNTAX	Integer32(-32768..32767)
	MAX-ACCESS	read-only
	STATUS	current
	DESCRIPTION	"DEC=0, UNIT='kVA'"
 ::= { groupRdCfg 18820 }

vUniGen1ActualQ	OBJECT-TYPE
	SYNTAX	Integer32(-32768..32767)
	MAX-ACCESS	read-only
	STATUS	current
	DESCRIPTION	"DEC=0, UNIT='kVAr'"
 ::= { groupRdCfg 18833 }

vUniGen2ActualQ	OBJECT-TYPE
	SYNTAX	Integer32(-32768..32767)
	MAX-ACCESS	read-only
	STATUS	current
	DESCRIPTION	"DEC=0, UNIT='kVAr'"
 ::= { groupRdCfg 18834 }

vUniGen3ActualQ	OBJECT-TYPE
	SYNTAX	Integer32(-32768..32767)
	MAX-ACCESS	read-only
	STATUS	current
	DESCRIPTION	"DEC=0, UNIT='kVAr'"
 ::= { groupRdCfg 18835 }

vUniGen4ActualQ	OBJECT-TYPE
	SYNTAX	Integer32(-32768..32767)
	MAX-ACCESS	read-only
	STATUS	current
	DESCRIPTION	"DEC=0, UNIT='kVAr'"
 ::= { groupRdCfg 18836 }

vUniGen1ActualP	OBJECT-TYPE
	SYNTAX	Integer32(-32768..32767)
	MAX-ACCESS	read-only
	STATUS	current
	DESCRIPTION	"DEC=0, UNIT='kW'"
 ::= { groupRdCfg 18849 }

vUniGen2ActualP	OBJECT-TYPE
	SYNTAX	Integer32(-32768..32767)
	MAX-ACCESS	read-only
	STATUS	current
	DESCRIPTION	"DEC=0, UNIT='kW'"
 ::= { groupRdCfg 18850 }

vUniGen3ActualP	OBJECT-TYPE
	SYNTAX	Integer32(-32768..32767)
	MAX-ACCESS	read-only
	STATUS	current
	DESCRIPTION	"DEC=0, UNIT='kW'"
 ::= { groupRdCfg 18851 }

vUniGen4ActualP	OBJECT-TYPE
	SYNTAX	Integer32(-32768..32767)
	MAX-ACCESS	read-only
	STATUS	current
	DESCRIPTION	"DEC=0, UNIT='kW'"
 ::= { groupRdCfg 18852 }

vUniGenRequestedP	OBJECT-TYPE
	SYNTAX	Integer32(-32768..32767)
	MAX-ACCESS	read-only
	STATUS	current
	DESCRIPTION	"DEC=0, UNIT='kW'"
 ::= { groupRdCfg 18865 }

vUniGen1RequestedQ	OBJECT-TYPE
	SYNTAX	Integer32(-32768..32767)
	MAX-ACCESS	read-only
	STATUS	current
	DESCRIPTION	"DEC=0, UNIT='kVAr'"
 ::= { groupRdCfg 18866 }

vUniGen2RequestedQ	OBJECT-TYPE
	SYNTAX	Integer32(-32768..32767)
	MAX-ACCESS	read-only
	STATUS	current
	DESCRIPTION	"DEC=0, UNIT='kVAr'"
 ::= { groupRdCfg 18867 }

vUniGen3RequestedQ	OBJECT-TYPE
	SYNTAX	Integer32(-32768..32767)
	MAX-ACCESS	read-only
	STATUS	current
	DESCRIPTION	"DEC=0, UNIT='kVAr'"
 ::= { groupRdCfg 18868 }

vUniGen4RequestedQ	OBJECT-TYPE
	SYNTAX	Integer32(-32768..32767)
	MAX-ACCESS	read-only
	STATUS	current
	DESCRIPTION	"DEC=0, UNIT='kVAr'"
 ::= { groupRdCfg 18869 }

vUniGen1RequestedP	OBJECT-TYPE
	SYNTAX	Integer32(-32768..32767)
	MAX-ACCESS	read-only
	STATUS	current
	DESCRIPTION	"DEC=0, UNIT='kW'"
 ::= { groupRdCfg 18882 }

vUniGen2RequestedP	OBJECT-TYPE
	SYNTAX	Integer32(-32768..32767)
	MAX-ACCESS	read-only
	STATUS	current
	DESCRIPTION	"DEC=0, UNIT='kW'"
 ::= { groupRdCfg 18883 }

vUniGen3RequestedP	OBJECT-TYPE
	SYNTAX	Integer32(-32768..32767)
	MAX-ACCESS	read-only
	STATUS	current
	DESCRIPTION	"DEC=0, UNIT='kW'"
 ::= { groupRdCfg 18884 }

vUniGen4RequestedP	OBJECT-TYPE
	SYNTAX	Integer32(-32768..32767)
	MAX-ACCESS	read-only
	STATUS	current
	DESCRIPTION	"DEC=0, UNIT='kW'"
 ::= { groupRdCfg 18885 }

vUniGenActualLoadCharacter	OBJECT-TYPE
	SYNTAX	DisplayString
	MAX-ACCESS	read-only
	STATUS	current
	DESCRIPTION	"String"
 ::= { groupRdCfg 18914 }

vUniGenActualPowerFactor	OBJECT-TYPE
	SYNTAX	Integer32(-32768..32767)
	MAX-ACCESS	read-only
	STATUS	current
	DESCRIPTION	"DEC=3, UNIT=''"
 ::= { groupRdCfg 18915 }

vUniGenActualS	OBJECT-TYPE
	SYNTAX	Integer32(-32768..32767)
	MAX-ACCESS	read-only
	STATUS	current
	DESCRIPTION	"DEC=0, UNIT='kVA'"
 ::= { groupRdCfg 18916 }

vUniGenActualQ	OBJECT-TYPE
	SYNTAX	Integer32(-32768..32767)
	MAX-ACCESS	read-only
	STATUS	current
	DESCRIPTION	"DEC=0, UNIT='kVAr'"
 ::= { groupRdCfg 18917 }

vUniGenActualP	OBJECT-TYPE
	SYNTAX	Integer32(-32768..32767)
	MAX-ACCESS	read-only
	STATUS	current
	DESCRIPTION	"DEC=0, UNIT='kW'"
 ::= { groupRdCfg 18918 }

vUniGenNominalP	OBJECT-TYPE
	SYNTAX	Integer32(0..65535)
	MAX-ACCESS	read-only
	STATUS	current
	DESCRIPTION	"DEC=0, UNIT='kW'"
 ::= { groupRdCfg 18919 }

vUniGen1ActualLoadCharacter	OBJECT-TYPE
	SYNTAX	DisplayString
	MAX-ACCESS	read-only
	STATUS	current
	DESCRIPTION	"String"
 ::= { groupRdCfg 18920 }

vUniGen2ActualLoadCharacter	OBJECT-TYPE
	SYNTAX	DisplayString
	MAX-ACCESS	read-only
	STATUS	current
	DESCRIPTION	"String"
 ::= { groupRdCfg 18921 }

vUniGen3ActualLoadCharacter	OBJECT-TYPE
	SYNTAX	DisplayString
	MAX-ACCESS	read-only
	STATUS	current
	DESCRIPTION	"String"
 ::= { groupRdCfg 18922 }

vUniGen4ActualLoadCharacter	OBJECT-TYPE
	SYNTAX	DisplayString
	MAX-ACCESS	read-only
	STATUS	current
	DESCRIPTION	"String"
 ::= { groupRdCfg 18923 }

vUniGen1ActualPowerFactor	OBJECT-TYPE
	SYNTAX	Integer32(-32768..32767)
	MAX-ACCESS	read-only
	STATUS	current
	DESCRIPTION	"DEC=3, UNIT=''"
 ::= { groupRdCfg 18936 }

vUniGen2ActualPowerFactor	OBJECT-TYPE
	SYNTAX	Integer32(-32768..32767)
	MAX-ACCESS	read-only
	STATUS	current
	DESCRIPTION	"DEC=3, UNIT=''"
 ::= { groupRdCfg 18937 }

vUniGen3ActualPowerFactor	OBJECT-TYPE
	SYNTAX	Integer32(-32768..32767)
	MAX-ACCESS	read-only
	STATUS	current
	DESCRIPTION	"DEC=3, UNIT=''"
 ::= { groupRdCfg 18938 }

vUniGen4ActualPowerFactor	OBJECT-TYPE
	SYNTAX	Integer32(-32768..32767)
	MAX-ACCESS	read-only
	STATUS	current
	DESCRIPTION	"DEC=3, UNIT=''"
 ::= { groupRdCfg 18939 }

vUniGenRelativeRequestedQ	OBJECT-TYPE
	SYNTAX	Integer32(-32768..32767)
	MAX-ACCESS	read-only
	STATUS	current
	DESCRIPTION	"DEC=2, UNIT='Percent'"
 ::= { groupRdCfg 18952 }

vUniGenRelativeRequestedP	OBJECT-TYPE
	SYNTAX	Integer32(-32768..32767)
	MAX-ACCESS	read-only
	STATUS	current
	DESCRIPTION	"DEC=2, UNIT='Percent'"
 ::= { groupRdCfg 18953 }

vUniGenRequestedQ	OBJECT-TYPE
	SYNTAX	Integer32(-32768..32767)
	MAX-ACCESS	read-only
	STATUS	current
	DESCRIPTION	"DEC=0, UNIT='kVAr'"
 ::= { groupRdCfg 18954 }

vUniGen1NominalP	OBJECT-TYPE
	SYNTAX	Integer32(0..65535)
	MAX-ACCESS	read-only
	STATUS	current
	DESCRIPTION	"DEC=0, UNIT='kW'"
 ::= { groupRdCfg 18955 }

vUniGen2NominalP	OBJECT-TYPE
	SYNTAX	Integer32(0..65535)
	MAX-ACCESS	read-only
	STATUS	current
	DESCRIPTION	"DEC=0, UNIT='kW'"
 ::= { groupRdCfg 18956 }

vUniGen3NominalP	OBJECT-TYPE
	SYNTAX	Integer32(0..65535)
	MAX-ACCESS	read-only
	STATUS	current
	DESCRIPTION	"DEC=0, UNIT='kW'"
 ::= { groupRdCfg 18957 }

vUniGen4NominalP	OBJECT-TYPE
	SYNTAX	Integer32(0..65535)
	MAX-ACCESS	read-only
	STATUS	current
	DESCRIPTION	"DEC=0, UNIT='kW'"
 ::= { groupRdCfg 18958 }

vECUAIN32288	OBJECT-TYPE
	SYNTAX	Integer32
	MAX-ACCESS	read-only
	STATUS	current
	DESCRIPTION	"DEC=0, UNIT=''"
 ::= { groupRdCfg 19150 }

vECUAIN32287	OBJECT-TYPE
	SYNTAX	Integer32
	MAX-ACCESS	read-only
	STATUS	current
	DESCRIPTION	"DEC=0, UNIT=''"
 ::= { groupRdCfg 19151 }

vECUAIN32286	OBJECT-TYPE
	SYNTAX	Integer32
	MAX-ACCESS	read-only
	STATUS	current
	DESCRIPTION	"DEC=0, UNIT=''"
 ::= { groupRdCfg 19152 }

vECUAIN32285	OBJECT-TYPE
	SYNTAX	Integer32
	MAX-ACCESS	read-only
	STATUS	current
	DESCRIPTION	"DEC=0, UNIT=''"
 ::= { groupRdCfg 19153 }

vECUAIN32284	OBJECT-TYPE
	SYNTAX	Integer32
	MAX-ACCESS	read-only
	STATUS	current
	DESCRIPTION	"DEC=0, UNIT=''"
 ::= { groupRdCfg 19154 }

vECUAIN32283	OBJECT-TYPE
	SYNTAX	Integer32
	MAX-ACCESS	read-only
	STATUS	current
	DESCRIPTION	"DEC=0, UNIT=''"
 ::= { groupRdCfg 19155 }

vECUAIN32282	OBJECT-TYPE
	SYNTAX	Integer32
	MAX-ACCESS	read-only
	STATUS	current
	DESCRIPTION	"DEC=0, UNIT=''"
 ::= { groupRdCfg 19156 }

vECUAIN32281	OBJECT-TYPE
	SYNTAX	Integer32
	MAX-ACCESS	read-only
	STATUS	current
	DESCRIPTION	"DEC=0, UNIT=''"
 ::= { groupRdCfg 19157 }

vECUAIN32280	OBJECT-TYPE
	SYNTAX	Integer32
	MAX-ACCESS	read-only
	STATUS	current
	DESCRIPTION	"DEC=0, UNIT=''"
 ::= { groupRdCfg 19158 }

vECUAIN32279	OBJECT-TYPE
	SYNTAX	Integer32
	MAX-ACCESS	read-only
	STATUS	current
	DESCRIPTION	"DEC=0, UNIT=''"
 ::= { groupRdCfg 19159 }

vECUAIN32278	OBJECT-TYPE
	SYNTAX	Integer32
	MAX-ACCESS	read-only
	STATUS	current
	DESCRIPTION	"DEC=0, UNIT=''"
 ::= { groupRdCfg 19160 }

vECUAIN32277	OBJECT-TYPE
	SYNTAX	Integer32
	MAX-ACCESS	read-only
	STATUS	current
	DESCRIPTION	"DEC=0, UNIT=''"
 ::= { groupRdCfg 19161 }

vECUAIN32276	OBJECT-TYPE
	SYNTAX	Integer32
	MAX-ACCESS	read-only
	STATUS	current
	DESCRIPTION	"DEC=0, UNIT=''"
 ::= { groupRdCfg 19162 }

vECUAIN32275	OBJECT-TYPE
	SYNTAX	Integer32
	MAX-ACCESS	read-only
	STATUS	current
	DESCRIPTION	"DEC=0, UNIT=''"
 ::= { groupRdCfg 19163 }

vECUAIN32274	OBJECT-TYPE
	SYNTAX	Integer32
	MAX-ACCESS	read-only
	STATUS	current
	DESCRIPTION	"DEC=0, UNIT=''"
 ::= { groupRdCfg 19164 }

vECUAIN32273	OBJECT-TYPE
	SYNTAX	Integer32
	MAX-ACCESS	read-only
	STATUS	current
	DESCRIPTION	"DEC=0, UNIT=''"
 ::= { groupRdCfg 19165 }

vECUAIN32272	OBJECT-TYPE
	SYNTAX	Integer32
	MAX-ACCESS	read-only
	STATUS	current
	DESCRIPTION	"DEC=0, UNIT=''"
 ::= { groupRdCfg 19166 }

vECUAIN32271	OBJECT-TYPE
	SYNTAX	Integer32
	MAX-ACCESS	read-only
	STATUS	current
	DESCRIPTION	"DEC=0, UNIT=''"
 ::= { groupRdCfg 19167 }

vECUAIN32270	OBJECT-TYPE
	SYNTAX	Integer32
	MAX-ACCESS	read-only
	STATUS	current
	DESCRIPTION	"DEC=0, UNIT=''"
 ::= { groupRdCfg 19168 }

vECUAIN32269	OBJECT-TYPE
	SYNTAX	Integer32
	MAX-ACCESS	read-only
	STATUS	current
	DESCRIPTION	"DEC=0, UNIT=''"
 ::= { groupRdCfg 19169 }

vECUAIN32268	OBJECT-TYPE
	SYNTAX	Integer32
	MAX-ACCESS	read-only
	STATUS	current
	DESCRIPTION	"DEC=0, UNIT=''"
 ::= { groupRdCfg 19170 }

vECUAIN32267	OBJECT-TYPE
	SYNTAX	Integer32
	MAX-ACCESS	read-only
	STATUS	current
	DESCRIPTION	"DEC=0, UNIT=''"
 ::= { groupRdCfg 19171 }

vECUAIN32266	OBJECT-TYPE
	SYNTAX	Integer32
	MAX-ACCESS	read-only
	STATUS	current
	DESCRIPTION	"DEC=0, UNIT=''"
 ::= { groupRdCfg 19172 }

vECUAIN32265	OBJECT-TYPE
	SYNTAX	Integer32
	MAX-ACCESS	read-only
	STATUS	current
	DESCRIPTION	"DEC=0, UNIT=''"
 ::= { groupRdCfg 19173 }

vECUAIN32264	OBJECT-TYPE
	SYNTAX	Integer32
	MAX-ACCESS	read-only
	STATUS	current
	DESCRIPTION	"DEC=0, UNIT=''"
 ::= { groupRdCfg 19174 }

vECUAIN32263	OBJECT-TYPE
	SYNTAX	Integer32
	MAX-ACCESS	read-only
	STATUS	current
	DESCRIPTION	"DEC=0, UNIT=''"
 ::= { groupRdCfg 19175 }

vECUAIN32262	OBJECT-TYPE
	SYNTAX	Integer32
	MAX-ACCESS	read-only
	STATUS	current
	DESCRIPTION	"DEC=0, UNIT=''"
 ::= { groupRdCfg 19176 }

vECUAIN32261	OBJECT-TYPE
	SYNTAX	Integer32
	MAX-ACCESS	read-only
	STATUS	current
	DESCRIPTION	"DEC=0, UNIT=''"
 ::= { groupRdCfg 19177 }

vECUAIN32260	OBJECT-TYPE
	SYNTAX	Integer32
	MAX-ACCESS	read-only
	STATUS	current
	DESCRIPTION	"DEC=0, UNIT=''"
 ::= { groupRdCfg 19178 }

vECUAIN32259	OBJECT-TYPE
	SYNTAX	Integer32
	MAX-ACCESS	read-only
	STATUS	current
	DESCRIPTION	"DEC=0, UNIT=''"
 ::= { groupRdCfg 19179 }

vECUAIN32258	OBJECT-TYPE
	SYNTAX	Integer32
	MAX-ACCESS	read-only
	STATUS	current
	DESCRIPTION	"DEC=0, UNIT=''"
 ::= { groupRdCfg 19180 }

vECUAIN32257	OBJECT-TYPE
	SYNTAX	Integer32
	MAX-ACCESS	read-only
	STATUS	current
	DESCRIPTION	"DEC=0, UNIT=''"
 ::= { groupRdCfg 19181 }

vECUAIN32256	OBJECT-TYPE
	SYNTAX	Integer32
	MAX-ACCESS	read-only
	STATUS	current
	DESCRIPTION	"DEC=0, UNIT=''"
 ::= { groupRdCfg 19182 }

vECUAIN32255	OBJECT-TYPE
	SYNTAX	Integer32
	MAX-ACCESS	read-only
	STATUS	current
	DESCRIPTION	"DEC=0, UNIT=''"
 ::= { groupRdCfg 19183 }

vECUAIN32254	OBJECT-TYPE
	SYNTAX	Integer32
	MAX-ACCESS	read-only
	STATUS	current
	DESCRIPTION	"DEC=0, UNIT=''"
 ::= { groupRdCfg 19184 }

vECUAIN32253	OBJECT-TYPE
	SYNTAX	Integer32
	MAX-ACCESS	read-only
	STATUS	current
	DESCRIPTION	"DEC=0, UNIT=''"
 ::= { groupRdCfg 19185 }

vECUAIN32252	OBJECT-TYPE
	SYNTAX	Integer32
	MAX-ACCESS	read-only
	STATUS	current
	DESCRIPTION	"DEC=0, UNIT=''"
 ::= { groupRdCfg 19186 }

vECUAIN32251	OBJECT-TYPE
	SYNTAX	Integer32
	MAX-ACCESS	read-only
	STATUS	current
	DESCRIPTION	"DEC=0, UNIT=''"
 ::= { groupRdCfg 19187 }

vECUAIN32250	OBJECT-TYPE
	SYNTAX	Integer32
	MAX-ACCESS	read-only
	STATUS	current
	DESCRIPTION	"DEC=0, UNIT=''"
 ::= { groupRdCfg 19188 }

vECUAIN32249	OBJECT-TYPE
	SYNTAX	Integer32
	MAX-ACCESS	read-only
	STATUS	current
	DESCRIPTION	"DEC=0, UNIT=''"
 ::= { groupRdCfg 19189 }

vECUAIN32248	OBJECT-TYPE
	SYNTAX	Integer32
	MAX-ACCESS	read-only
	STATUS	current
	DESCRIPTION	"DEC=0, UNIT=''"
 ::= { groupRdCfg 19190 }

vECUAIN32247	OBJECT-TYPE
	SYNTAX	Integer32
	MAX-ACCESS	read-only
	STATUS	current
	DESCRIPTION	"DEC=0, UNIT=''"
 ::= { groupRdCfg 19191 }

vECUAIN32246	OBJECT-TYPE
	SYNTAX	Integer32
	MAX-ACCESS	read-only
	STATUS	current
	DESCRIPTION	"DEC=0, UNIT=''"
 ::= { groupRdCfg 19192 }

vECUAIN32245	OBJECT-TYPE
	SYNTAX	Integer32
	MAX-ACCESS	read-only
	STATUS	current
	DESCRIPTION	"DEC=0, UNIT=''"
 ::= { groupRdCfg 19193 }

vECUAIN32244	OBJECT-TYPE
	SYNTAX	Integer32
	MAX-ACCESS	read-only
	STATUS	current
	DESCRIPTION	"DEC=0, UNIT=''"
 ::= { groupRdCfg 19194 }

vECUAIN32243	OBJECT-TYPE
	SYNTAX	Integer32
	MAX-ACCESS	read-only
	STATUS	current
	DESCRIPTION	"DEC=0, UNIT=''"
 ::= { groupRdCfg 19195 }

vECUAIN32242	OBJECT-TYPE
	SYNTAX	Integer32
	MAX-ACCESS	read-only
	STATUS	current
	DESCRIPTION	"DEC=0, UNIT=''"
 ::= { groupRdCfg 19196 }

vECUAIN32241	OBJECT-TYPE
	SYNTAX	Integer32
	MAX-ACCESS	read-only
	STATUS	current
	DESCRIPTION	"DEC=0, UNIT=''"
 ::= { groupRdCfg 19197 }

vECUAIN32240	OBJECT-TYPE
	SYNTAX	Integer32
	MAX-ACCESS	read-only
	STATUS	current
	DESCRIPTION	"DEC=0, UNIT=''"
 ::= { groupRdCfg 19198 }

vECUAIN32239	OBJECT-TYPE
	SYNTAX	Integer32
	MAX-ACCESS	read-only
	STATUS	current
	DESCRIPTION	"DEC=0, UNIT=''"
 ::= { groupRdCfg 19199 }

vECUAIN32238	OBJECT-TYPE
	SYNTAX	Integer32
	MAX-ACCESS	read-only
	STATUS	current
	DESCRIPTION	"DEC=0, UNIT=''"
 ::= { groupRdCfg 19200 }

vECUAIN32237	OBJECT-TYPE
	SYNTAX	Integer32
	MAX-ACCESS	read-only
	STATUS	current
	DESCRIPTION	"DEC=0, UNIT=''"
 ::= { groupRdCfg 19201 }

vECUAIN32236	OBJECT-TYPE
	SYNTAX	Integer32
	MAX-ACCESS	read-only
	STATUS	current
	DESCRIPTION	"DEC=0, UNIT=''"
 ::= { groupRdCfg 19202 }

vECUAIN32235	OBJECT-TYPE
	SYNTAX	Integer32
	MAX-ACCESS	read-only
	STATUS	current
	DESCRIPTION	"DEC=0, UNIT=''"
 ::= { groupRdCfg 19203 }

vECUAIN32234	OBJECT-TYPE
	SYNTAX	Integer32
	MAX-ACCESS	read-only
	STATUS	current
	DESCRIPTION	"DEC=0, UNIT=''"
 ::= { groupRdCfg 19204 }

vECUAIN32233	OBJECT-TYPE
	SYNTAX	Integer32
	MAX-ACCESS	read-only
	STATUS	current
	DESCRIPTION	"DEC=0, UNIT=''"
 ::= { groupRdCfg 19205 }

vECUAIN32232	OBJECT-TYPE
	SYNTAX	Integer32
	MAX-ACCESS	read-only
	STATUS	current
	DESCRIPTION	"DEC=0, UNIT=''"
 ::= { groupRdCfg 19206 }

vECUAIN32231	OBJECT-TYPE
	SYNTAX	Integer32
	MAX-ACCESS	read-only
	STATUS	current
	DESCRIPTION	"DEC=0, UNIT=''"
 ::= { groupRdCfg 19207 }

vECUAIN32230	OBJECT-TYPE
	SYNTAX	Integer32
	MAX-ACCESS	read-only
	STATUS	current
	DESCRIPTION	"DEC=0, UNIT=''"
 ::= { groupRdCfg 19208 }

vECUAIN32229	OBJECT-TYPE
	SYNTAX	Integer32
	MAX-ACCESS	read-only
	STATUS	current
	DESCRIPTION	"DEC=0, UNIT=''"
 ::= { groupRdCfg 19209 }

vECUAIN32228	OBJECT-TYPE
	SYNTAX	Integer32
	MAX-ACCESS	read-only
	STATUS	current
	DESCRIPTION	"DEC=0, UNIT=''"
 ::= { groupRdCfg 19210 }

vECUAIN32227	OBJECT-TYPE
	SYNTAX	Integer32
	MAX-ACCESS	read-only
	STATUS	current
	DESCRIPTION	"DEC=0, UNIT=''"
 ::= { groupRdCfg 19211 }

vECUAIN32226	OBJECT-TYPE
	SYNTAX	Integer32
	MAX-ACCESS	read-only
	STATUS	current
	DESCRIPTION	"DEC=0, UNIT=''"
 ::= { groupRdCfg 19212 }

vECUAIN32225	OBJECT-TYPE
	SYNTAX	Integer32
	MAX-ACCESS	read-only
	STATUS	current
	DESCRIPTION	"DEC=0, UNIT=''"
 ::= { groupRdCfg 19213 }

vECUAIN32224	OBJECT-TYPE
	SYNTAX	Integer32
	MAX-ACCESS	read-only
	STATUS	current
	DESCRIPTION	"DEC=0, UNIT=''"
 ::= { groupRdCfg 19214 }

vECUAIN32223	OBJECT-TYPE
	SYNTAX	Integer32
	MAX-ACCESS	read-only
	STATUS	current
	DESCRIPTION	"DEC=0, UNIT=''"
 ::= { groupRdCfg 19215 }

vECUAIN32222	OBJECT-TYPE
	SYNTAX	Integer32
	MAX-ACCESS	read-only
	STATUS	current
	DESCRIPTION	"DEC=0, UNIT=''"
 ::= { groupRdCfg 19216 }

vECUAIN32221	OBJECT-TYPE
	SYNTAX	Integer32
	MAX-ACCESS	read-only
	STATUS	current
	DESCRIPTION	"DEC=0, UNIT=''"
 ::= { groupRdCfg 19217 }

vECUAIN32220	OBJECT-TYPE
	SYNTAX	Integer32
	MAX-ACCESS	read-only
	STATUS	current
	DESCRIPTION	"DEC=0, UNIT=''"
 ::= { groupRdCfg 19218 }

vECUAIN32219	OBJECT-TYPE
	SYNTAX	Integer32
	MAX-ACCESS	read-only
	STATUS	current
	DESCRIPTION	"DEC=0, UNIT=''"
 ::= { groupRdCfg 19219 }

vECUAIN32218	OBJECT-TYPE
	SYNTAX	Integer32
	MAX-ACCESS	read-only
	STATUS	current
	DESCRIPTION	"DEC=0, UNIT=''"
 ::= { groupRdCfg 19220 }

vECUAIN32217	OBJECT-TYPE
	SYNTAX	Integer32
	MAX-ACCESS	read-only
	STATUS	current
	DESCRIPTION	"DEC=0, UNIT=''"
 ::= { groupRdCfg 19221 }

vECUAIN32216	OBJECT-TYPE
	SYNTAX	Integer32
	MAX-ACCESS	read-only
	STATUS	current
	DESCRIPTION	"DEC=0, UNIT=''"
 ::= { groupRdCfg 19222 }

vECUAIN32215	OBJECT-TYPE
	SYNTAX	Integer32
	MAX-ACCESS	read-only
	STATUS	current
	DESCRIPTION	"DEC=0, UNIT=''"
 ::= { groupRdCfg 19223 }

vECUAIN32214	OBJECT-TYPE
	SYNTAX	Integer32
	MAX-ACCESS	read-only
	STATUS	current
	DESCRIPTION	"DEC=0, UNIT=''"
 ::= { groupRdCfg 19224 }

vECUAIN32213	OBJECT-TYPE
	SYNTAX	Integer32
	MAX-ACCESS	read-only
	STATUS	current
	DESCRIPTION	"DEC=0, UNIT=''"
 ::= { groupRdCfg 19225 }

vECUAIN32212	OBJECT-TYPE
	SYNTAX	Integer32
	MAX-ACCESS	read-only
	STATUS	current
	DESCRIPTION	"DEC=0, UNIT=''"
 ::= { groupRdCfg 19226 }

vECUAIN32211	OBJECT-TYPE
	SYNTAX	Integer32
	MAX-ACCESS	read-only
	STATUS	current
	DESCRIPTION	"DEC=0, UNIT=''"
 ::= { groupRdCfg 19227 }

vECUAIN32210	OBJECT-TYPE
	SYNTAX	Integer32
	MAX-ACCESS	read-only
	STATUS	current
	DESCRIPTION	"DEC=0, UNIT=''"
 ::= { groupRdCfg 19228 }

vECUAIN32209	OBJECT-TYPE
	SYNTAX	Integer32
	MAX-ACCESS	read-only
	STATUS	current
	DESCRIPTION	"DEC=0, UNIT=''"
 ::= { groupRdCfg 19229 }

vECUAIN32208	OBJECT-TYPE
	SYNTAX	Integer32
	MAX-ACCESS	read-only
	STATUS	current
	DESCRIPTION	"DEC=0, UNIT=''"
 ::= { groupRdCfg 19230 }

vECUAIN32207	OBJECT-TYPE
	SYNTAX	Integer32
	MAX-ACCESS	read-only
	STATUS	current
	DESCRIPTION	"DEC=0, UNIT=''"
 ::= { groupRdCfg 19231 }

vECUAIN32206	OBJECT-TYPE
	SYNTAX	Integer32
	MAX-ACCESS	read-only
	STATUS	current
	DESCRIPTION	"DEC=0, UNIT=''"
 ::= { groupRdCfg 19232 }

vECUAIN32205	OBJECT-TYPE
	SYNTAX	Integer32
	MAX-ACCESS	read-only
	STATUS	current
	DESCRIPTION	"DEC=0, UNIT=''"
 ::= { groupRdCfg 19233 }

vECUAIN32204	OBJECT-TYPE
	SYNTAX	Integer32
	MAX-ACCESS	read-only
	STATUS	current
	DESCRIPTION	"DEC=0, UNIT=''"
 ::= { groupRdCfg 19234 }

vECUAIN32203	OBJECT-TYPE
	SYNTAX	Integer32
	MAX-ACCESS	read-only
	STATUS	current
	DESCRIPTION	"DEC=0, UNIT=''"
 ::= { groupRdCfg 19235 }

vECUAIN32202	OBJECT-TYPE
	SYNTAX	Integer32
	MAX-ACCESS	read-only
	STATUS	current
	DESCRIPTION	"DEC=0, UNIT=''"
 ::= { groupRdCfg 19236 }

vECUAIN32201	OBJECT-TYPE
	SYNTAX	Integer32
	MAX-ACCESS	read-only
	STATUS	current
	DESCRIPTION	"DEC=0, UNIT=''"
 ::= { groupRdCfg 19237 }

vECUAIN32200	OBJECT-TYPE
	SYNTAX	Integer32
	MAX-ACCESS	read-only
	STATUS	current
	DESCRIPTION	"DEC=0, UNIT=''"
 ::= { groupRdCfg 19238 }

vECUAIN32199	OBJECT-TYPE
	SYNTAX	Integer32
	MAX-ACCESS	read-only
	STATUS	current
	DESCRIPTION	"DEC=0, UNIT=''"
 ::= { groupRdCfg 19239 }

vECUAIN32198	OBJECT-TYPE
	SYNTAX	Integer32
	MAX-ACCESS	read-only
	STATUS	current
	DESCRIPTION	"DEC=0, UNIT=''"
 ::= { groupRdCfg 19240 }

vECUAIN32197	OBJECT-TYPE
	SYNTAX	Integer32
	MAX-ACCESS	read-only
	STATUS	current
	DESCRIPTION	"DEC=0, UNIT=''"
 ::= { groupRdCfg 19241 }

vECUAIN32196	OBJECT-TYPE
	SYNTAX	Integer32
	MAX-ACCESS	read-only
	STATUS	current
	DESCRIPTION	"DEC=0, UNIT=''"
 ::= { groupRdCfg 19242 }

vECUAIN32195	OBJECT-TYPE
	SYNTAX	Integer32
	MAX-ACCESS	read-only
	STATUS	current
	DESCRIPTION	"DEC=0, UNIT=''"
 ::= { groupRdCfg 19243 }

vECUAIN32194	OBJECT-TYPE
	SYNTAX	Integer32
	MAX-ACCESS	read-only
	STATUS	current
	DESCRIPTION	"DEC=0, UNIT=''"
 ::= { groupRdCfg 19244 }

vECUAIN32193	OBJECT-TYPE
	SYNTAX	Integer32
	MAX-ACCESS	read-only
	STATUS	current
	DESCRIPTION	"DEC=0, UNIT=''"
 ::= { groupRdCfg 19245 }

vECUAIN32192	OBJECT-TYPE
	SYNTAX	Integer32
	MAX-ACCESS	read-only
	STATUS	current
	DESCRIPTION	"DEC=0, UNIT=''"
 ::= { groupRdCfg 19246 }

vECUAIN32191	OBJECT-TYPE
	SYNTAX	Integer32
	MAX-ACCESS	read-only
	STATUS	current
	DESCRIPTION	"DEC=0, UNIT=''"
 ::= { groupRdCfg 19247 }

vECUAIN32190	OBJECT-TYPE
	SYNTAX	Integer32
	MAX-ACCESS	read-only
	STATUS	current
	DESCRIPTION	"DEC=0, UNIT=''"
 ::= { groupRdCfg 19248 }

vECUAIN32189	OBJECT-TYPE
	SYNTAX	Integer32
	MAX-ACCESS	read-only
	STATUS	current
	DESCRIPTION	"DEC=0, UNIT=''"
 ::= { groupRdCfg 19249 }

vECUAIN32188	OBJECT-TYPE
	SYNTAX	Integer32
	MAX-ACCESS	read-only
	STATUS	current
	DESCRIPTION	"DEC=0, UNIT=''"
 ::= { groupRdCfg 19250 }

vECUAIN32187	OBJECT-TYPE
	SYNTAX	Integer32
	MAX-ACCESS	read-only
	STATUS	current
	DESCRIPTION	"DEC=0, UNIT=''"
 ::= { groupRdCfg 19251 }

vECUAIN32186	OBJECT-TYPE
	SYNTAX	Integer32
	MAX-ACCESS	read-only
	STATUS	current
	DESCRIPTION	"DEC=0, UNIT=''"
 ::= { groupRdCfg 19252 }

vECUAIN32185	OBJECT-TYPE
	SYNTAX	Integer32
	MAX-ACCESS	read-only
	STATUS	current
	DESCRIPTION	"DEC=0, UNIT=''"
 ::= { groupRdCfg 19253 }

vECUAIN32184	OBJECT-TYPE
	SYNTAX	Integer32
	MAX-ACCESS	read-only
	STATUS	current
	DESCRIPTION	"DEC=0, UNIT=''"
 ::= { groupRdCfg 19254 }

vECUAIN32183	OBJECT-TYPE
	SYNTAX	Integer32
	MAX-ACCESS	read-only
	STATUS	current
	DESCRIPTION	"DEC=0, UNIT=''"
 ::= { groupRdCfg 19255 }

vECUAIN32182	OBJECT-TYPE
	SYNTAX	Integer32
	MAX-ACCESS	read-only
	STATUS	current
	DESCRIPTION	"DEC=0, UNIT=''"
 ::= { groupRdCfg 19256 }

vECUAIN32181	OBJECT-TYPE
	SYNTAX	Integer32
	MAX-ACCESS	read-only
	STATUS	current
	DESCRIPTION	"DEC=0, UNIT=''"
 ::= { groupRdCfg 19257 }

vECUAIN32180	OBJECT-TYPE
	SYNTAX	Integer32
	MAX-ACCESS	read-only
	STATUS	current
	DESCRIPTION	"DEC=0, UNIT=''"
 ::= { groupRdCfg 19258 }

vECUAIN32179	OBJECT-TYPE
	SYNTAX	Integer32
	MAX-ACCESS	read-only
	STATUS	current
	DESCRIPTION	"DEC=0, UNIT=''"
 ::= { groupRdCfg 19259 }

vECUAIN32178	OBJECT-TYPE
	SYNTAX	Integer32
	MAX-ACCESS	read-only
	STATUS	current
	DESCRIPTION	"DEC=0, UNIT=''"
 ::= { groupRdCfg 19260 }

vECUAIN32177	OBJECT-TYPE
	SYNTAX	Integer32
	MAX-ACCESS	read-only
	STATUS	current
	DESCRIPTION	"DEC=0, UNIT=''"
 ::= { groupRdCfg 19261 }

vECUAIN32176	OBJECT-TYPE
	SYNTAX	Integer32
	MAX-ACCESS	read-only
	STATUS	current
	DESCRIPTION	"DEC=0, UNIT=''"
 ::= { groupRdCfg 19262 }

vECUAIN32175	OBJECT-TYPE
	SYNTAX	Integer32
	MAX-ACCESS	read-only
	STATUS	current
	DESCRIPTION	"DEC=0, UNIT=''"
 ::= { groupRdCfg 19263 }

vECUAIN32174	OBJECT-TYPE
	SYNTAX	Integer32
	MAX-ACCESS	read-only
	STATUS	current
	DESCRIPTION	"DEC=0, UNIT=''"
 ::= { groupRdCfg 19264 }

vECUAIN32173	OBJECT-TYPE
	SYNTAX	Integer32
	MAX-ACCESS	read-only
	STATUS	current
	DESCRIPTION	"DEC=0, UNIT=''"
 ::= { groupRdCfg 19265 }

vECUAIN32172	OBJECT-TYPE
	SYNTAX	Integer32
	MAX-ACCESS	read-only
	STATUS	current
	DESCRIPTION	"DEC=0, UNIT=''"
 ::= { groupRdCfg 19266 }

vECUAIN32171	OBJECT-TYPE
	SYNTAX	Integer32
	MAX-ACCESS	read-only
	STATUS	current
	DESCRIPTION	"DEC=0, UNIT=''"
 ::= { groupRdCfg 19267 }

vECUAIN32170	OBJECT-TYPE
	SYNTAX	Integer32
	MAX-ACCESS	read-only
	STATUS	current
	DESCRIPTION	"DEC=0, UNIT=''"
 ::= { groupRdCfg 19268 }

vECUAIN32169	OBJECT-TYPE
	SYNTAX	Integer32
	MAX-ACCESS	read-only
	STATUS	current
	DESCRIPTION	"DEC=0, UNIT=''"
 ::= { groupRdCfg 19269 }

vECUAIN32168	OBJECT-TYPE
	SYNTAX	Integer32
	MAX-ACCESS	read-only
	STATUS	current
	DESCRIPTION	"DEC=0, UNIT=''"
 ::= { groupRdCfg 19270 }

vECUAIN32167	OBJECT-TYPE
	SYNTAX	Integer32
	MAX-ACCESS	read-only
	STATUS	current
	DESCRIPTION	"DEC=0, UNIT=''"
 ::= { groupRdCfg 19271 }

vECUAIN32166	OBJECT-TYPE
	SYNTAX	Integer32
	MAX-ACCESS	read-only
	STATUS	current
	DESCRIPTION	"DEC=0, UNIT=''"
 ::= { groupRdCfg 19272 }

vECUAIN32165	OBJECT-TYPE
	SYNTAX	Integer32
	MAX-ACCESS	read-only
	STATUS	current
	DESCRIPTION	"DEC=0, UNIT=''"
 ::= { groupRdCfg 19273 }

vECUAIN32164	OBJECT-TYPE
	SYNTAX	Integer32
	MAX-ACCESS	read-only
	STATUS	current
	DESCRIPTION	"DEC=0, UNIT=''"
 ::= { groupRdCfg 19274 }

vECUAIN32163	OBJECT-TYPE
	SYNTAX	Integer32
	MAX-ACCESS	read-only
	STATUS	current
	DESCRIPTION	"DEC=0, UNIT=''"
 ::= { groupRdCfg 19275 }

vECUAIN32162	OBJECT-TYPE
	SYNTAX	Integer32
	MAX-ACCESS	read-only
	STATUS	current
	DESCRIPTION	"DEC=0, UNIT=''"
 ::= { groupRdCfg 19276 }

vECUAIN32161	OBJECT-TYPE
	SYNTAX	Integer32
	MAX-ACCESS	read-only
	STATUS	current
	DESCRIPTION	"DEC=0, UNIT=''"
 ::= { groupRdCfg 19277 }

vECUAIN32160	OBJECT-TYPE
	SYNTAX	Integer32
	MAX-ACCESS	read-only
	STATUS	current
	DESCRIPTION	"DEC=0, UNIT=''"
 ::= { groupRdCfg 19278 }

vECUAIN32159	OBJECT-TYPE
	SYNTAX	Integer32
	MAX-ACCESS	read-only
	STATUS	current
	DESCRIPTION	"DEC=0, UNIT=''"
 ::= { groupRdCfg 19279 }

vECUAIN32158	OBJECT-TYPE
	SYNTAX	Integer32
	MAX-ACCESS	read-only
	STATUS	current
	DESCRIPTION	"DEC=0, UNIT=''"
 ::= { groupRdCfg 19280 }

vECUAIN32157	OBJECT-TYPE
	SYNTAX	Integer32
	MAX-ACCESS	read-only
	STATUS	current
	DESCRIPTION	"DEC=0, UNIT=''"
 ::= { groupRdCfg 19281 }

vECUAIN32156	OBJECT-TYPE
	SYNTAX	Integer32
	MAX-ACCESS	read-only
	STATUS	current
	DESCRIPTION	"DEC=0, UNIT=''"
 ::= { groupRdCfg 19282 }

vECUAIN32155	OBJECT-TYPE
	SYNTAX	Integer32
	MAX-ACCESS	read-only
	STATUS	current
	DESCRIPTION	"DEC=0, UNIT=''"
 ::= { groupRdCfg 19283 }

vECUAIN32154	OBJECT-TYPE
	SYNTAX	Integer32
	MAX-ACCESS	read-only
	STATUS	current
	DESCRIPTION	"DEC=0, UNIT=''"
 ::= { groupRdCfg 19284 }

vECUAIN32153	OBJECT-TYPE
	SYNTAX	Integer32
	MAX-ACCESS	read-only
	STATUS	current
	DESCRIPTION	"DEC=0, UNIT=''"
 ::= { groupRdCfg 19285 }

vECUAIN32152	OBJECT-TYPE
	SYNTAX	Integer32
	MAX-ACCESS	read-only
	STATUS	current
	DESCRIPTION	"DEC=0, UNIT=''"
 ::= { groupRdCfg 19286 }

vECUAIN32151	OBJECT-TYPE
	SYNTAX	Integer32
	MAX-ACCESS	read-only
	STATUS	current
	DESCRIPTION	"DEC=0, UNIT=''"
 ::= { groupRdCfg 19287 }

vECUAIN32150	OBJECT-TYPE
	SYNTAX	Integer32
	MAX-ACCESS	read-only
	STATUS	current
	DESCRIPTION	"DEC=0, UNIT=''"
 ::= { groupRdCfg 19288 }

vECUAIN32149	OBJECT-TYPE
	SYNTAX	Integer32
	MAX-ACCESS	read-only
	STATUS	current
	DESCRIPTION	"DEC=0, UNIT=''"
 ::= { groupRdCfg 19289 }

vECUAIN32148	OBJECT-TYPE
	SYNTAX	Integer32
	MAX-ACCESS	read-only
	STATUS	current
	DESCRIPTION	"DEC=0, UNIT=''"
 ::= { groupRdCfg 19290 }

vECUAIN32147	OBJECT-TYPE
	SYNTAX	Integer32
	MAX-ACCESS	read-only
	STATUS	current
	DESCRIPTION	"DEC=0, UNIT=''"
 ::= { groupRdCfg 19291 }

vECUAIN32146	OBJECT-TYPE
	SYNTAX	Integer32
	MAX-ACCESS	read-only
	STATUS	current
	DESCRIPTION	"DEC=0, UNIT=''"
 ::= { groupRdCfg 19292 }

vECUAIN32145	OBJECT-TYPE
	SYNTAX	Integer32
	MAX-ACCESS	read-only
	STATUS	current
	DESCRIPTION	"DEC=0, UNIT=''"
 ::= { groupRdCfg 19293 }

vECUAIN32144	OBJECT-TYPE
	SYNTAX	Integer32
	MAX-ACCESS	read-only
	STATUS	current
	DESCRIPTION	"DEC=0, UNIT=''"
 ::= { groupRdCfg 19294 }

vECUAIN32143	OBJECT-TYPE
	SYNTAX	Integer32
	MAX-ACCESS	read-only
	STATUS	current
	DESCRIPTION	"DEC=0, UNIT=''"
 ::= { groupRdCfg 19295 }

vECUAIN32142	OBJECT-TYPE
	SYNTAX	Integer32
	MAX-ACCESS	read-only
	STATUS	current
	DESCRIPTION	"DEC=0, UNIT=''"
 ::= { groupRdCfg 19296 }

vECUAIN32141	OBJECT-TYPE
	SYNTAX	Integer32
	MAX-ACCESS	read-only
	STATUS	current
	DESCRIPTION	"DEC=0, UNIT=''"
 ::= { groupRdCfg 19297 }

vECUAIN32140	OBJECT-TYPE
	SYNTAX	Integer32
	MAX-ACCESS	read-only
	STATUS	current
	DESCRIPTION	"DEC=0, UNIT=''"
 ::= { groupRdCfg 19298 }

vECUAIN32139	OBJECT-TYPE
	SYNTAX	Integer32
	MAX-ACCESS	read-only
	STATUS	current
	DESCRIPTION	"DEC=0, UNIT=''"
 ::= { groupRdCfg 19299 }

vECUAIN32138	OBJECT-TYPE
	SYNTAX	Integer32
	MAX-ACCESS	read-only
	STATUS	current
	DESCRIPTION	"DEC=0, UNIT=''"
 ::= { groupRdCfg 19300 }

vECUAIN32137	OBJECT-TYPE
	SYNTAX	Integer32
	MAX-ACCESS	read-only
	STATUS	current
	DESCRIPTION	"DEC=0, UNIT=''"
 ::= { groupRdCfg 19301 }

vECUAIN32136	OBJECT-TYPE
	SYNTAX	Integer32
	MAX-ACCESS	read-only
	STATUS	current
	DESCRIPTION	"DEC=0, UNIT=''"
 ::= { groupRdCfg 19302 }

vECUAIN32135	OBJECT-TYPE
	SYNTAX	Integer32
	MAX-ACCESS	read-only
	STATUS	current
	DESCRIPTION	"DEC=0, UNIT=''"
 ::= { groupRdCfg 19303 }

vECUAIN32134	OBJECT-TYPE
	SYNTAX	Integer32
	MAX-ACCESS	read-only
	STATUS	current
	DESCRIPTION	"DEC=0, UNIT=''"
 ::= { groupRdCfg 19304 }

vECUAIN32133	OBJECT-TYPE
	SYNTAX	Integer32
	MAX-ACCESS	read-only
	STATUS	current
	DESCRIPTION	"DEC=0, UNIT=''"
 ::= { groupRdCfg 19305 }

vECUAIN32132	OBJECT-TYPE
	SYNTAX	Integer32
	MAX-ACCESS	read-only
	STATUS	current
	DESCRIPTION	"DEC=0, UNIT=''"
 ::= { groupRdCfg 19306 }

vECUAIN32131	OBJECT-TYPE
	SYNTAX	Integer32
	MAX-ACCESS	read-only
	STATUS	current
	DESCRIPTION	"DEC=0, UNIT=''"
 ::= { groupRdCfg 19307 }

vECUAIN32130	OBJECT-TYPE
	SYNTAX	Integer32
	MAX-ACCESS	read-only
	STATUS	current
	DESCRIPTION	"DEC=0, UNIT=''"
 ::= { groupRdCfg 19308 }

vECUAIN32129	OBJECT-TYPE
	SYNTAX	Integer32
	MAX-ACCESS	read-only
	STATUS	current
	DESCRIPTION	"DEC=0, UNIT=''"
 ::= { groupRdCfg 19309 }

vECUAIN32128	OBJECT-TYPE
	SYNTAX	Integer32
	MAX-ACCESS	read-only
	STATUS	current
	DESCRIPTION	"DEC=0, UNIT=''"
 ::= { groupRdCfg 19310 }

vECUAIN32127	OBJECT-TYPE
	SYNTAX	Integer32
	MAX-ACCESS	read-only
	STATUS	current
	DESCRIPTION	"DEC=0, UNIT=''"
 ::= { groupRdCfg 19311 }

vECUAIN32126	OBJECT-TYPE
	SYNTAX	Integer32
	MAX-ACCESS	read-only
	STATUS	current
	DESCRIPTION	"DEC=0, UNIT=''"
 ::= { groupRdCfg 19312 }

vECUAIN32125	OBJECT-TYPE
	SYNTAX	Integer32
	MAX-ACCESS	read-only
	STATUS	current
	DESCRIPTION	"DEC=0, UNIT=''"
 ::= { groupRdCfg 19313 }

vECUAIN32124	OBJECT-TYPE
	SYNTAX	Integer32
	MAX-ACCESS	read-only
	STATUS	current
	DESCRIPTION	"DEC=0, UNIT=''"
 ::= { groupRdCfg 19314 }

vECUAIN32123	OBJECT-TYPE
	SYNTAX	Integer32
	MAX-ACCESS	read-only
	STATUS	current
	DESCRIPTION	"DEC=0, UNIT=''"
 ::= { groupRdCfg 19315 }

vECUAIN32122	OBJECT-TYPE
	SYNTAX	Integer32
	MAX-ACCESS	read-only
	STATUS	current
	DESCRIPTION	"DEC=0, UNIT=''"
 ::= { groupRdCfg 19316 }

vECUAIN32121	OBJECT-TYPE
	SYNTAX	Integer32
	MAX-ACCESS	read-only
	STATUS	current
	DESCRIPTION	"DEC=0, UNIT=''"
 ::= { groupRdCfg 19317 }

vECUAIN32120	OBJECT-TYPE
	SYNTAX	Integer32
	MAX-ACCESS	read-only
	STATUS	current
	DESCRIPTION	"DEC=0, UNIT=''"
 ::= { groupRdCfg 19318 }

vECUAIN32119	OBJECT-TYPE
	SYNTAX	Integer32
	MAX-ACCESS	read-only
	STATUS	current
	DESCRIPTION	"DEC=0, UNIT=''"
 ::= { groupRdCfg 19319 }

vECUAIN32118	OBJECT-TYPE
	SYNTAX	Integer32
	MAX-ACCESS	read-only
	STATUS	current
	DESCRIPTION	"DEC=0, UNIT=''"
 ::= { groupRdCfg 19320 }

vECUAIN32117	OBJECT-TYPE
	SYNTAX	Integer32
	MAX-ACCESS	read-only
	STATUS	current
	DESCRIPTION	"DEC=0, UNIT=''"
 ::= { groupRdCfg 19321 }

vECUAIN32116	OBJECT-TYPE
	SYNTAX	Integer32
	MAX-ACCESS	read-only
	STATUS	current
	DESCRIPTION	"DEC=0, UNIT=''"
 ::= { groupRdCfg 19322 }

vECUAIN32115	OBJECT-TYPE
	SYNTAX	Integer32
	MAX-ACCESS	read-only
	STATUS	current
	DESCRIPTION	"DEC=0, UNIT=''"
 ::= { groupRdCfg 19323 }

vECUAIN32114	OBJECT-TYPE
	SYNTAX	Integer32
	MAX-ACCESS	read-only
	STATUS	current
	DESCRIPTION	"DEC=0, UNIT=''"
 ::= { groupRdCfg 19324 }

vECUAIN32113	OBJECT-TYPE
	SYNTAX	Integer32
	MAX-ACCESS	read-only
	STATUS	current
	DESCRIPTION	"DEC=0, UNIT=''"
 ::= { groupRdCfg 19325 }

vECUAIN32112	OBJECT-TYPE
	SYNTAX	Integer32
	MAX-ACCESS	read-only
	STATUS	current
	DESCRIPTION	"DEC=0, UNIT=''"
 ::= { groupRdCfg 19326 }

vECUAIN32111	OBJECT-TYPE
	SYNTAX	Integer32
	MAX-ACCESS	read-only
	STATUS	current
	DESCRIPTION	"DEC=0, UNIT=''"
 ::= { groupRdCfg 19327 }

vECUAIN32110	OBJECT-TYPE
	SYNTAX	Integer32
	MAX-ACCESS	read-only
	STATUS	current
	DESCRIPTION	"DEC=0, UNIT=''"
 ::= { groupRdCfg 19328 }

vECUAIN32109	OBJECT-TYPE
	SYNTAX	Integer32
	MAX-ACCESS	read-only
	STATUS	current
	DESCRIPTION	"DEC=0, UNIT=''"
 ::= { groupRdCfg 19329 }

vECUAIN32108	OBJECT-TYPE
	SYNTAX	Integer32
	MAX-ACCESS	read-only
	STATUS	current
	DESCRIPTION	"DEC=0, UNIT=''"
 ::= { groupRdCfg 19330 }

vECUAIN32107	OBJECT-TYPE
	SYNTAX	Integer32
	MAX-ACCESS	read-only
	STATUS	current
	DESCRIPTION	"DEC=0, UNIT=''"
 ::= { groupRdCfg 19331 }

vECUAIN32106	OBJECT-TYPE
	SYNTAX	Integer32
	MAX-ACCESS	read-only
	STATUS	current
	DESCRIPTION	"DEC=0, UNIT=''"
 ::= { groupRdCfg 19332 }

vECUAIN32105	OBJECT-TYPE
	SYNTAX	Integer32
	MAX-ACCESS	read-only
	STATUS	current
	DESCRIPTION	"DEC=0, UNIT=''"
 ::= { groupRdCfg 19333 }

vECUAIN32104	OBJECT-TYPE
	SYNTAX	Integer32
	MAX-ACCESS	read-only
	STATUS	current
	DESCRIPTION	"DEC=0, UNIT=''"
 ::= { groupRdCfg 19334 }

vECUAIN32103	OBJECT-TYPE
	SYNTAX	Integer32
	MAX-ACCESS	read-only
	STATUS	current
	DESCRIPTION	"DEC=0, UNIT=''"
 ::= { groupRdCfg 19335 }

vECUAIN32102	OBJECT-TYPE
	SYNTAX	Integer32
	MAX-ACCESS	read-only
	STATUS	current
	DESCRIPTION	"DEC=0, UNIT=''"
 ::= { groupRdCfg 19336 }

vECUAIN32101	OBJECT-TYPE
	SYNTAX	Integer32
	MAX-ACCESS	read-only
	STATUS	current
	DESCRIPTION	"DEC=0, UNIT=''"
 ::= { groupRdCfg 19337 }

vECUAIN32100	OBJECT-TYPE
	SYNTAX	Integer32
	MAX-ACCESS	read-only
	STATUS	current
	DESCRIPTION	"DEC=0, UNIT=''"
 ::= { groupRdCfg 19338 }

vECUAIN3299	OBJECT-TYPE
	SYNTAX	Integer32
	MAX-ACCESS	read-only
	STATUS	current
	DESCRIPTION	"DEC=0, UNIT=''"
 ::= { groupRdCfg 19339 }

vECUAIN3298	OBJECT-TYPE
	SYNTAX	Integer32
	MAX-ACCESS	read-only
	STATUS	current
	DESCRIPTION	"DEC=0, UNIT=''"
 ::= { groupRdCfg 19340 }

vECUAIN3297	OBJECT-TYPE
	SYNTAX	Integer32
	MAX-ACCESS	read-only
	STATUS	current
	DESCRIPTION	"DEC=0, UNIT=''"
 ::= { groupRdCfg 19341 }

vECUAIN3296	OBJECT-TYPE
	SYNTAX	Integer32
	MAX-ACCESS	read-only
	STATUS	current
	DESCRIPTION	"DEC=0, UNIT=''"
 ::= { groupRdCfg 19342 }

vECUAIN3295	OBJECT-TYPE
	SYNTAX	Integer32
	MAX-ACCESS	read-only
	STATUS	current
	DESCRIPTION	"DEC=0, UNIT=''"
 ::= { groupRdCfg 19343 }

vECUAIN3294	OBJECT-TYPE
	SYNTAX	Integer32
	MAX-ACCESS	read-only
	STATUS	current
	DESCRIPTION	"DEC=0, UNIT=''"
 ::= { groupRdCfg 19344 }

vECUAIN3293	OBJECT-TYPE
	SYNTAX	Integer32
	MAX-ACCESS	read-only
	STATUS	current
	DESCRIPTION	"DEC=0, UNIT=''"
 ::= { groupRdCfg 19345 }

vECUAIN3292	OBJECT-TYPE
	SYNTAX	Integer32
	MAX-ACCESS	read-only
	STATUS	current
	DESCRIPTION	"DEC=0, UNIT=''"
 ::= { groupRdCfg 19346 }

vECUAIN3291	OBJECT-TYPE
	SYNTAX	Integer32
	MAX-ACCESS	read-only
	STATUS	current
	DESCRIPTION	"DEC=0, UNIT=''"
 ::= { groupRdCfg 19347 }

vECUAIN3290	OBJECT-TYPE
	SYNTAX	Integer32
	MAX-ACCESS	read-only
	STATUS	current
	DESCRIPTION	"DEC=0, UNIT=''"
 ::= { groupRdCfg 19348 }

vECUAIN3289	OBJECT-TYPE
	SYNTAX	Integer32
	MAX-ACCESS	read-only
	STATUS	current
	DESCRIPTION	"DEC=0, UNIT=''"
 ::= { groupRdCfg 19349 }

vECUAIN3288	OBJECT-TYPE
	SYNTAX	Integer32
	MAX-ACCESS	read-only
	STATUS	current
	DESCRIPTION	"DEC=0, UNIT=''"
 ::= { groupRdCfg 19350 }

vECUAIN3287	OBJECT-TYPE
	SYNTAX	Integer32
	MAX-ACCESS	read-only
	STATUS	current
	DESCRIPTION	"DEC=0, UNIT=''"
 ::= { groupRdCfg 19351 }

vECUAIN3286	OBJECT-TYPE
	SYNTAX	Integer32
	MAX-ACCESS	read-only
	STATUS	current
	DESCRIPTION	"DEC=0, UNIT=''"
 ::= { groupRdCfg 19352 }

vECUAIN3285	OBJECT-TYPE
	SYNTAX	Integer32
	MAX-ACCESS	read-only
	STATUS	current
	DESCRIPTION	"DEC=0, UNIT=''"
 ::= { groupRdCfg 19353 }

vECUAIN3284	OBJECT-TYPE
	SYNTAX	Integer32
	MAX-ACCESS	read-only
	STATUS	current
	DESCRIPTION	"DEC=0, UNIT=''"
 ::= { groupRdCfg 19354 }

vECUAIN3283	OBJECT-TYPE
	SYNTAX	Integer32
	MAX-ACCESS	read-only
	STATUS	current
	DESCRIPTION	"DEC=0, UNIT=''"
 ::= { groupRdCfg 19355 }

vECUAIN3282	OBJECT-TYPE
	SYNTAX	Integer32
	MAX-ACCESS	read-only
	STATUS	current
	DESCRIPTION	"DEC=0, UNIT=''"
 ::= { groupRdCfg 19356 }

vECUAIN3281	OBJECT-TYPE
	SYNTAX	Integer32
	MAX-ACCESS	read-only
	STATUS	current
	DESCRIPTION	"DEC=0, UNIT=''"
 ::= { groupRdCfg 19357 }

vECUAIN3280	OBJECT-TYPE
	SYNTAX	Integer32
	MAX-ACCESS	read-only
	STATUS	current
	DESCRIPTION	"DEC=0, UNIT=''"
 ::= { groupRdCfg 19358 }

vECUAIN3279	OBJECT-TYPE
	SYNTAX	Integer32
	MAX-ACCESS	read-only
	STATUS	current
	DESCRIPTION	"DEC=0, UNIT=''"
 ::= { groupRdCfg 19359 }

vECUAIN3278	OBJECT-TYPE
	SYNTAX	Integer32
	MAX-ACCESS	read-only
	STATUS	current
	DESCRIPTION	"DEC=0, UNIT=''"
 ::= { groupRdCfg 19360 }

vECUAIN3277	OBJECT-TYPE
	SYNTAX	Integer32
	MAX-ACCESS	read-only
	STATUS	current
	DESCRIPTION	"DEC=0, UNIT=''"
 ::= { groupRdCfg 19361 }

vECUAIN3276	OBJECT-TYPE
	SYNTAX	Integer32
	MAX-ACCESS	read-only
	STATUS	current
	DESCRIPTION	"DEC=0, UNIT=''"
 ::= { groupRdCfg 19362 }

vECUAIN3275	OBJECT-TYPE
	SYNTAX	Integer32
	MAX-ACCESS	read-only
	STATUS	current
	DESCRIPTION	"DEC=0, UNIT=''"
 ::= { groupRdCfg 19363 }

vECUAIN3274	OBJECT-TYPE
	SYNTAX	Integer32
	MAX-ACCESS	read-only
	STATUS	current
	DESCRIPTION	"DEC=0, UNIT=''"
 ::= { groupRdCfg 19364 }

vECUAIN3273	OBJECT-TYPE
	SYNTAX	Integer32
	MAX-ACCESS	read-only
	STATUS	current
	DESCRIPTION	"DEC=0, UNIT=''"
 ::= { groupRdCfg 19365 }

vECUAIN3272	OBJECT-TYPE
	SYNTAX	Integer32
	MAX-ACCESS	read-only
	STATUS	current
	DESCRIPTION	"DEC=0, UNIT=''"
 ::= { groupRdCfg 19366 }

vECUAIN3271	OBJECT-TYPE
	SYNTAX	Integer32
	MAX-ACCESS	read-only
	STATUS	current
	DESCRIPTION	"DEC=0, UNIT=''"
 ::= { groupRdCfg 19367 }

vECUAIN3270	OBJECT-TYPE
	SYNTAX	Integer32
	MAX-ACCESS	read-only
	STATUS	current
	DESCRIPTION	"DEC=0, UNIT=''"
 ::= { groupRdCfg 19368 }

vECUAIN3269	OBJECT-TYPE
	SYNTAX	Integer32
	MAX-ACCESS	read-only
	STATUS	current
	DESCRIPTION	"DEC=0, UNIT=''"
 ::= { groupRdCfg 19369 }

vECUAIN3268	OBJECT-TYPE
	SYNTAX	Integer32
	MAX-ACCESS	read-only
	STATUS	current
	DESCRIPTION	"DEC=0, UNIT=''"
 ::= { groupRdCfg 19370 }

vECUAIN3267	OBJECT-TYPE
	SYNTAX	Integer32
	MAX-ACCESS	read-only
	STATUS	current
	DESCRIPTION	"DEC=0, UNIT=''"
 ::= { groupRdCfg 19371 }

vECUAIN3266	OBJECT-TYPE
	SYNTAX	Integer32
	MAX-ACCESS	read-only
	STATUS	current
	DESCRIPTION	"DEC=0, UNIT=''"
 ::= { groupRdCfg 19372 }

vECUAIN3265	OBJECT-TYPE
	SYNTAX	Integer32
	MAX-ACCESS	read-only
	STATUS	current
	DESCRIPTION	"DEC=0, UNIT=''"
 ::= { groupRdCfg 19373 }

vECUAIN3264	OBJECT-TYPE
	SYNTAX	Integer32
	MAX-ACCESS	read-only
	STATUS	current
	DESCRIPTION	"DEC=0, UNIT=''"
 ::= { groupRdCfg 19374 }

vECUAIN3263	OBJECT-TYPE
	SYNTAX	Integer32
	MAX-ACCESS	read-only
	STATUS	current
	DESCRIPTION	"DEC=0, UNIT=''"
 ::= { groupRdCfg 19375 }

vECUAIN3262	OBJECT-TYPE
	SYNTAX	Integer32
	MAX-ACCESS	read-only
	STATUS	current
	DESCRIPTION	"DEC=0, UNIT=''"
 ::= { groupRdCfg 19376 }

vECUAIN3261	OBJECT-TYPE
	SYNTAX	Integer32
	MAX-ACCESS	read-only
	STATUS	current
	DESCRIPTION	"DEC=0, UNIT=''"
 ::= { groupRdCfg 19377 }

vECUAIN3260	OBJECT-TYPE
	SYNTAX	Integer32
	MAX-ACCESS	read-only
	STATUS	current
	DESCRIPTION	"DEC=0, UNIT=''"
 ::= { groupRdCfg 19378 }

vECUAIN3259	OBJECT-TYPE
	SYNTAX	Integer32
	MAX-ACCESS	read-only
	STATUS	current
	DESCRIPTION	"DEC=0, UNIT=''"
 ::= { groupRdCfg 19379 }

vECUAIN3258	OBJECT-TYPE
	SYNTAX	Integer32
	MAX-ACCESS	read-only
	STATUS	current
	DESCRIPTION	"DEC=0, UNIT=''"
 ::= { groupRdCfg 19380 }

vECUAIN3257	OBJECT-TYPE
	SYNTAX	Integer32
	MAX-ACCESS	read-only
	STATUS	current
	DESCRIPTION	"DEC=0, UNIT=''"
 ::= { groupRdCfg 19381 }

vECUAIN3256	OBJECT-TYPE
	SYNTAX	Integer32
	MAX-ACCESS	read-only
	STATUS	current
	DESCRIPTION	"DEC=0, UNIT=''"
 ::= { groupRdCfg 19382 }

vECUAIN3255	OBJECT-TYPE
	SYNTAX	Integer32
	MAX-ACCESS	read-only
	STATUS	current
	DESCRIPTION	"DEC=0, UNIT=''"
 ::= { groupRdCfg 19383 }

vECUAIN3254	OBJECT-TYPE
	SYNTAX	Integer32
	MAX-ACCESS	read-only
	STATUS	current
	DESCRIPTION	"DEC=0, UNIT=''"
 ::= { groupRdCfg 19384 }

vECUAIN3253	OBJECT-TYPE
	SYNTAX	Integer32
	MAX-ACCESS	read-only
	STATUS	current
	DESCRIPTION	"DEC=0, UNIT=''"
 ::= { groupRdCfg 19385 }

vECUAIN3252	OBJECT-TYPE
	SYNTAX	Integer32
	MAX-ACCESS	read-only
	STATUS	current
	DESCRIPTION	"DEC=0, UNIT=''"
 ::= { groupRdCfg 19386 }

vECUAIN3251	OBJECT-TYPE
	SYNTAX	Integer32
	MAX-ACCESS	read-only
	STATUS	current
	DESCRIPTION	"DEC=0, UNIT=''"
 ::= { groupRdCfg 19387 }

vECUAIN3250	OBJECT-TYPE
	SYNTAX	Integer32
	MAX-ACCESS	read-only
	STATUS	current
	DESCRIPTION	"DEC=0, UNIT=''"
 ::= { groupRdCfg 19388 }

vECUAIN3249	OBJECT-TYPE
	SYNTAX	Integer32
	MAX-ACCESS	read-only
	STATUS	current
	DESCRIPTION	"DEC=0, UNIT=''"
 ::= { groupRdCfg 19389 }

vECUAIN3248	OBJECT-TYPE
	SYNTAX	Integer32
	MAX-ACCESS	read-only
	STATUS	current
	DESCRIPTION	"DEC=0, UNIT=''"
 ::= { groupRdCfg 19390 }

vECUAIN3247	OBJECT-TYPE
	SYNTAX	Integer32
	MAX-ACCESS	read-only
	STATUS	current
	DESCRIPTION	"DEC=0, UNIT=''"
 ::= { groupRdCfg 19391 }

vECUAIN3246	OBJECT-TYPE
	SYNTAX	Integer32
	MAX-ACCESS	read-only
	STATUS	current
	DESCRIPTION	"DEC=0, UNIT=''"
 ::= { groupRdCfg 19392 }

vECUAIN3245	OBJECT-TYPE
	SYNTAX	Integer32
	MAX-ACCESS	read-only
	STATUS	current
	DESCRIPTION	"DEC=0, UNIT=''"
 ::= { groupRdCfg 19393 }

vECUAIN3244	OBJECT-TYPE
	SYNTAX	Integer32
	MAX-ACCESS	read-only
	STATUS	current
	DESCRIPTION	"DEC=0, UNIT=''"
 ::= { groupRdCfg 19394 }

vECUAIN3243	OBJECT-TYPE
	SYNTAX	Integer32
	MAX-ACCESS	read-only
	STATUS	current
	DESCRIPTION	"DEC=0, UNIT=''"
 ::= { groupRdCfg 19395 }

vECUAIN3242	OBJECT-TYPE
	SYNTAX	Integer32
	MAX-ACCESS	read-only
	STATUS	current
	DESCRIPTION	"DEC=0, UNIT=''"
 ::= { groupRdCfg 19396 }

vECUAIN3241	OBJECT-TYPE
	SYNTAX	Integer32
	MAX-ACCESS	read-only
	STATUS	current
	DESCRIPTION	"DEC=0, UNIT=''"
 ::= { groupRdCfg 19397 }

vECUAIN3240	OBJECT-TYPE
	SYNTAX	Integer32
	MAX-ACCESS	read-only
	STATUS	current
	DESCRIPTION	"DEC=0, UNIT=''"
 ::= { groupRdCfg 19398 }

vECUAIN3239	OBJECT-TYPE
	SYNTAX	Integer32
	MAX-ACCESS	read-only
	STATUS	current
	DESCRIPTION	"DEC=0, UNIT=''"
 ::= { groupRdCfg 19399 }

vECUAIN3238	OBJECT-TYPE
	SYNTAX	Integer32
	MAX-ACCESS	read-only
	STATUS	current
	DESCRIPTION	"DEC=0, UNIT=''"
 ::= { groupRdCfg 19400 }

vECUAIN3237	OBJECT-TYPE
	SYNTAX	Integer32
	MAX-ACCESS	read-only
	STATUS	current
	DESCRIPTION	"DEC=0, UNIT=''"
 ::= { groupRdCfg 19401 }

vReactivePower	OBJECT-TYPE
	SYNTAX	Integer32
	MAX-ACCESS	read-only
	STATUS	current
	DESCRIPTION	"DEC=1, UNIT='kVAr'"
 ::= { groupRdCfg 19402 }

vECUAIN3235	OBJECT-TYPE
	SYNTAX	Integer32
	MAX-ACCESS	read-only
	STATUS	current
	DESCRIPTION	"DEC=0, UNIT=''"
 ::= { groupRdCfg 19403 }

vGridFrequency	OBJECT-TYPE
	SYNTAX	Integer32
	MAX-ACCESS	read-only
	STATUS	current
	DESCRIPTION	"DEC=2, UNIT='Hz'"
 ::= { groupRdCfg 19404 }

vGridVoltageL3L1	OBJECT-TYPE
	SYNTAX	Integer32
	MAX-ACCESS	read-only
	STATUS	current
	DESCRIPTION	"DEC=1, UNIT='V'"
 ::= { groupRdCfg 19405 }

vGridVoltageL2L3	OBJECT-TYPE
	SYNTAX	Integer32
	MAX-ACCESS	read-only
	STATUS	current
	DESCRIPTION	"DEC=1, UNIT='V'"
 ::= { groupRdCfg 19406 }

vGridVoltageL1L2	OBJECT-TYPE
	SYNTAX	Integer32
	MAX-ACCESS	read-only
	STATUS	current
	DESCRIPTION	"DEC=1, UNIT='V'"
 ::= { groupRdCfg 19407 }

vActivePower	OBJECT-TYPE
	SYNTAX	Integer32
	MAX-ACCESS	read-only
	STATUS	current
	DESCRIPTION	"DEC=1, UNIT='kW'"
 ::= { groupRdCfg 19408 }

vECUAIN3229	OBJECT-TYPE
	SYNTAX	Integer32
	MAX-ACCESS	read-only
	STATUS	current
	DESCRIPTION	"DEC=0, UNIT=''"
 ::= { groupRdCfg 19409 }

vCurrentL3	OBJECT-TYPE
	SYNTAX	Integer32
	MAX-ACCESS	read-only
	STATUS	current
	DESCRIPTION	"DEC=1, UNIT='A'"
 ::= { groupRdCfg 19410 }

vCurrentL2	OBJECT-TYPE
	SYNTAX	Integer32
	MAX-ACCESS	read-only
	STATUS	current
	DESCRIPTION	"DEC=1, UNIT='A'"
 ::= { groupRdCfg 19411 }

vCurrentL1	OBJECT-TYPE
	SYNTAX	Integer32
	MAX-ACCESS	read-only
	STATUS	current
	DESCRIPTION	"DEC=1, UNIT='A'"
 ::= { groupRdCfg 19412 }

vECUAIN3225	OBJECT-TYPE
	SYNTAX	Integer32
	MAX-ACCESS	read-only
	STATUS	current
	DESCRIPTION	"DEC=0, UNIT=''"
 ::= { groupRdCfg 19413 }

vSOH	OBJECT-TYPE
	SYNTAX	Integer32
	MAX-ACCESS	read-only
	STATUS	current
	DESCRIPTION	"DEC=0, UNIT='Percent'"
 ::= { groupRdCfg 19414 }

vSOC	OBJECT-TYPE
	SYNTAX	Integer32
	MAX-ACCESS	read-only
	STATUS	current
	DESCRIPTION	"DEC=0, UNIT='Percent'"
 ::= { groupRdCfg 19415 }

vECUAIN3222	OBJECT-TYPE
	SYNTAX	Integer32
	MAX-ACCESS	read-only
	STATUS	current
	DESCRIPTION	"DEC=0, UNIT=''"
 ::= { groupRdCfg 19416 }

vECUAIN3221	OBJECT-TYPE
	SYNTAX	Integer32
	MAX-ACCESS	read-only
	STATUS	current
	DESCRIPTION	"DEC=0, UNIT=''"
 ::= { groupRdCfg 19417 }

vReleasedEnergy	OBJECT-TYPE
	SYNTAX	Integer32
	MAX-ACCESS	read-only
	STATUS	current
	DESCRIPTION	"DEC=0, UNIT='kWh'"
 ::= { groupRdCfg 19418 }

vAbsorbedEnergy	OBJECT-TYPE
	SYNTAX	Integer32
	MAX-ACCESS	read-only
	STATUS	current
	DESCRIPTION	"DEC=0, UNIT='kWh'"
 ::= { groupRdCfg 19419 }

vACTNRJEXPORT	OBJECT-TYPE
	SYNTAX	Integer32
	MAX-ACCESS	read-only
	STATUS	current
	DESCRIPTION	"DEC=2, UNIT='kWh'"
 ::= { groupRdCfg 19420 }

vACTNRJIMPORT	OBJECT-TYPE
	SYNTAX	Integer32
	MAX-ACCESS	read-only
	STATUS	current
	DESCRIPTION	"DEC=2, UNIT='kWh'"
 ::= { groupRdCfg 19421 }

vREACTPOWER	OBJECT-TYPE
	SYNTAX	Integer32
	MAX-ACCESS	read-only
	STATUS	current
	DESCRIPTION	"DEC=2, UNIT='kVAr'"
 ::= { groupRdCfg 19422 }

vREACTPercent	OBJECT-TYPE
	SYNTAX	Integer32
	MAX-ACCESS	read-only
	STATUS	current
	DESCRIPTION	"DEC=1, UNIT='Percent'"
 ::= { groupRdCfg 19423 }

vACTPOWER	OBJECT-TYPE
	SYNTAX	Integer32
	MAX-ACCESS	read-only
	STATUS	current
	DESCRIPTION	"DEC=2, UNIT='kW'"
 ::= { groupRdCfg 19424 }

vTOTKWhPV1	OBJECT-TYPE
	SYNTAX	Integer32
	MAX-ACCESS	read-only
	STATUS	current
	DESCRIPTION	"DEC=1, UNIT='kWh'"
 ::= { groupRdCfg 19425 }

vTOTKWhPV2	OBJECT-TYPE
	SYNTAX	Integer32
	MAX-ACCESS	read-only
	STATUS	current
	DESCRIPTION	"DEC=1, UNIT='kWh'"
 ::= { groupRdCfg 19426 }

vPFSET	OBJECT-TYPE
	SYNTAX	Integer32
	MAX-ACCESS	read-only
	STATUS	current
	DESCRIPTION	"DEC=3, UNIT=''"
 ::= { groupRdCfg 19427 }

vREACTPercent	OBJECT-TYPE
	SYNTAX	Integer32
	MAX-ACCESS	read-only
	STATUS	current
	DESCRIPTION	"DEC=1, UNIT='Percent'"
 ::= { groupRdCfg 19428 }

vRealTimeActivePowerPercent	OBJECT-TYPE
	SYNTAX	Integer32
	MAX-ACCESS	read-only
	STATUS	current
	DESCRIPTION	"DEC=0, UNIT=''"
 ::= { groupRdCfg 19429 }

vReactivePower	OBJECT-TYPE
	SYNTAX	Integer32
	MAX-ACCESS	read-only
	STATUS	current
	DESCRIPTION	"DEC=1, UNIT='kVAr'"
 ::= { groupRdCfg 19430 }

vActivePower	OBJECT-TYPE
	SYNTAX	Integer32
	MAX-ACCESS	read-only
	STATUS	current
	DESCRIPTION	"DEC=1, UNIT='kW'"
 ::= { groupRdCfg 19431 }

vInputPower	OBJECT-TYPE
	SYNTAX	Integer32
	MAX-ACCESS	read-only
	STATUS	current
	DESCRIPTION	"DEC=1, UNIT='kW'"
 ::= { groupRdCfg 19432 }

vMaximumApparentPower	OBJECT-TYPE
	SYNTAX	Integer32
	MAX-ACCESS	read-only
	STATUS	current
	DESCRIPTION	"DEC=1, UNIT='kVA'"
 ::= { groupRdCfg 19433 }

vMaximumActivePower	OBJECT-TYPE
	SYNTAX	Integer32
	MAX-ACCESS	read-only
	STATUS	current
	DESCRIPTION	"DEC=1, UNIT='kW'"
 ::= { groupRdCfg 19434 }

vNominalActivePower	OBJECT-TYPE
	SYNTAX	Integer32
	MAX-ACCESS	read-only
	STATUS	current
	DESCRIPTION	"DEC=1, UNIT='kW'"
 ::= { groupRdCfg 19435 }

vReactivePower	OBJECT-TYPE
	SYNTAX	Integer32
	MAX-ACCESS	read-only
	STATUS	current
	DESCRIPTION	"DEC=1, UNIT='kVAr'"
 ::= { groupRdCfg 19436 }

vActivePower	OBJECT-TYPE
	SYNTAX	Integer32
	MAX-ACCESS	read-only
	STATUS	current
	DESCRIPTION	"DEC=1, UNIT='kW'"
 ::= { groupRdCfg 19437 }

vBESSVoltageRequired	OBJECT-TYPE
	SYNTAX	Integer32
	MAX-ACCESS	read-only
	STATUS	current
	DESCRIPTION	"DEC=2, UNIT='V'"
 ::= { groupRdCfg 19443 }

vBESSVoltageOffset	OBJECT-TYPE
	SYNTAX	Integer32
	MAX-ACCESS	read-only
	STATUS	current
	DESCRIPTION	"DEC=2, UNIT='V'"
 ::= { groupRdCfg 19444 }

vBESSQRequiredPercent	OBJECT-TYPE
	SYNTAX	Integer32(-32768..32767)
	MAX-ACCESS	read-only
	STATUS	current
	DESCRIPTION	"DEC=1, UNIT='Percent'"
 ::= { groupRdCfg 19445 }

vBESSFrequencyRequired	OBJECT-TYPE
	SYNTAX	Integer32
	MAX-ACCESS	read-only
	STATUS	current
	DESCRIPTION	"DEC=2, UNIT='Hz'"
 ::= { groupRdCfg 19446 }

vBESSFrequencyOffset	OBJECT-TYPE
	SYNTAX	Integer32
	MAX-ACCESS	read-only
	STATUS	current
	DESCRIPTION	"DEC=2, UNIT='Hz'"
 ::= { groupRdCfg 19447 }

vBESSPRequired	OBJECT-TYPE
	SYNTAX	Integer32(-32768..32767)
	MAX-ACCESS	read-only
	STATUS	current
	DESCRIPTION	"DEC=1, UNIT='Percent'"
 ::= { groupRdCfg 19448 }

vPVTotalCurtailedKWh	OBJECT-TYPE
	SYNTAX	Gauge32
	MAX-ACCESS	read-only
	STATUS	current
	DESCRIPTION	"DEC=0, UNIT='kWh'"
 ::= { groupRdCfg 19548 }

vPVCurtailedAnnualKWh	OBJECT-TYPE
	SYNTAX	Gauge32
	MAX-ACCESS	read-only
	STATUS	current
	DESCRIPTION	"DEC=0, UNIT='kWh'"
 ::= { groupRdCfg 19549 }

vPVCurtailedMonthlyKWh	OBJECT-TYPE
	SYNTAX	Gauge32
	MAX-ACCESS	read-only
	STATUS	current
	DESCRIPTION	"DEC=0, UNIT='kWh'"
 ::= { groupRdCfg 19550 }

vPVCurtailedWeeklyKWh	OBJECT-TYPE
	SYNTAX	Gauge32
	MAX-ACCESS	read-only
	STATUS	current
	DESCRIPTION	"DEC=0, UNIT='kWh'"
 ::= { groupRdCfg 19551 }

vPVCurtailedDailyKWh	OBJECT-TYPE
	SYNTAX	Gauge32
	MAX-ACCESS	read-only
	STATUS	current
	DESCRIPTION	"DEC=0, UNIT='kWh'"
 ::= { groupRdCfg 19552 }

vPVMaxP	OBJECT-TYPE
	SYNTAX	Integer32(0..65535)
	MAX-ACCESS	read-only
	STATUS	current
	DESCRIPTION	"DEC=0, UNIT='kW'"
 ::= { groupRdCfg 19553 }

vPVCurtailedP	OBJECT-TYPE
	SYNTAX	Integer32(0..65535)
	MAX-ACCESS	read-only
	STATUS	current
	DESCRIPTION	"DEC=0, UNIT='kW'"
 ::= { groupRdCfg 19554 }

vPVCurtailedPRelative	OBJECT-TYPE
	SYNTAX	Integer32(0..65535)
	MAX-ACCESS	read-only
	STATUS	current
	DESCRIPTION	"DEC=0, UNIT='Percent'"
 ::= { groupRdCfg 19555 }

vExerciseTimer1	OBJECT-TYPE
	SYNTAX	OCTET STRING
	MAX-ACCESS	read-only
	STATUS	current
	DESCRIPTION	"Time"
 ::= { groupRdCfg 19664 }

vExerciseTimer2	OBJECT-TYPE
	SYNTAX	OCTET STRING
	MAX-ACCESS	read-only
	STATUS	current
	DESCRIPTION	"Time"
 ::= { groupRdCfg 19665 }

vExerciseTimer3	OBJECT-TYPE
	SYNTAX	OCTET STRING
	MAX-ACCESS	read-only
	STATUS	current
	DESCRIPTION	"Time"
 ::= { groupRdCfg 19666 }

vExerciseTimer4	OBJECT-TYPE
	SYNTAX	OCTET STRING
	MAX-ACCESS	read-only
	STATUS	current
	DESCRIPTION	"Time"
 ::= { groupRdCfg 19667 }

vExerciseTimer5	OBJECT-TYPE
	SYNTAX	OCTET STRING
	MAX-ACCESS	read-only
	STATUS	current
	DESCRIPTION	"Time"
 ::= { groupRdCfg 19668 }

vExerciseTimer6	OBJECT-TYPE
	SYNTAX	OCTET STRING
	MAX-ACCESS	read-only
	STATUS	current
	DESCRIPTION	"Time"
 ::= { groupRdCfg 19669 }

vRENActualLoadCharacter	OBJECT-TYPE
	SYNTAX	DisplayString
	MAX-ACCESS	read-only
	STATUS	current
	DESCRIPTION	"String"
 ::= { groupRdCfg 19724 }

vRENActualPowerFactor	OBJECT-TYPE
	SYNTAX	Integer32(-32768..32767)
	MAX-ACCESS	read-only
	STATUS	current
	DESCRIPTION	"DEC=3, UNIT=''"
 ::= { groupRdCfg 19725 }

vRENActualS	OBJECT-TYPE
	SYNTAX	Integer32(-32768..32767)
	MAX-ACCESS	read-only
	STATUS	current
	DESCRIPTION	"DEC=0, UNIT='kVA'"
 ::= { groupRdCfg 19726 }

vRENActualQ	OBJECT-TYPE
	SYNTAX	Integer32(-32768..32767)
	MAX-ACCESS	read-only
	STATUS	current
	DESCRIPTION	"DEC=0, UNIT='kVAr'"
 ::= { groupRdCfg 19727 }

vRENActualP	OBJECT-TYPE
	SYNTAX	Integer32(-32768..32767)
	MAX-ACCESS	read-only
	STATUS	current
	DESCRIPTION	"DEC=0, UNIT='kW'"
 ::= { groupRdCfg 19728 }

vRENNominalP	OBJECT-TYPE
	SYNTAX	Integer32(0..65535)
	MAX-ACCESS	read-only
	STATUS	current
	DESCRIPTION	"DEC=0, UNIT='kW'"
 ::= { groupRdCfg 19729 }

vWTActualLoadCharacter	OBJECT-TYPE
	SYNTAX	DisplayString
	MAX-ACCESS	read-only
	STATUS	current
	DESCRIPTION	"String"
 ::= { groupRdCfg 19730 }

vWTActualPowerFactor	OBJECT-TYPE
	SYNTAX	Integer32(-32768..32767)
	MAX-ACCESS	read-only
	STATUS	current
	DESCRIPTION	"DEC=3, UNIT=''"
 ::= { groupRdCfg 19731 }

vWTActualS	OBJECT-TYPE
	SYNTAX	Integer32(-32768..32767)
	MAX-ACCESS	read-only
	STATUS	current
	DESCRIPTION	"DEC=0, UNIT='kVA'"
 ::= { groupRdCfg 19732 }

vWTActualQ	OBJECT-TYPE
	SYNTAX	Integer32(-32768..32767)
	MAX-ACCESS	read-only
	STATUS	current
	DESCRIPTION	"DEC=0, UNIT='kVAr'"
 ::= { groupRdCfg 19733 }

vWTActualP	OBJECT-TYPE
	SYNTAX	Integer32(-32768..32767)
	MAX-ACCESS	read-only
	STATUS	current
	DESCRIPTION	"DEC=0, UNIT='kW'"
 ::= { groupRdCfg 19734 }

vWTNominalP	OBJECT-TYPE
	SYNTAX	Integer32(0..65535)
	MAX-ACCESS	read-only
	STATUS	current
	DESCRIPTION	"DEC=0, UNIT='kW'"
 ::= { groupRdCfg 19735 }

vWT2ActualLoadCharacter	OBJECT-TYPE
	SYNTAX	DisplayString
	MAX-ACCESS	read-only
	STATUS	current
	DESCRIPTION	"String"
 ::= { groupRdCfg 19772 }

vWT2ActualPowerFactor	OBJECT-TYPE
	SYNTAX	Integer32(-32768..32767)
	MAX-ACCESS	read-only
	STATUS	current
	DESCRIPTION	"DEC=3, UNIT=''"
 ::= { groupRdCfg 19773 }

vWT2ActualS	OBJECT-TYPE
	SYNTAX	Integer32(-32768..32767)
	MAX-ACCESS	read-only
	STATUS	current
	DESCRIPTION	"DEC=0, UNIT='kVA'"
 ::= { groupRdCfg 19774 }

vWT2ActualQ	OBJECT-TYPE
	SYNTAX	Integer32(-32768..32767)
	MAX-ACCESS	read-only
	STATUS	current
	DESCRIPTION	"DEC=0, UNIT='kVAr'"
 ::= { groupRdCfg 19775 }

vWT2ActualP	OBJECT-TYPE
	SYNTAX	Integer32(-32768..32767)
	MAX-ACCESS	read-only
	STATUS	current
	DESCRIPTION	"DEC=0, UNIT='kW'"
 ::= { groupRdCfg 19776 }

vWT2NominalP	OBJECT-TYPE
	SYNTAX	Integer32(0..65535)
	MAX-ACCESS	read-only
	STATUS	current
	DESCRIPTION	"DEC=0, UNIT='kW'"
 ::= { groupRdCfg 19777 }

vWT1ActualLoadCharacter	OBJECT-TYPE
	SYNTAX	DisplayString
	MAX-ACCESS	read-only
	STATUS	current
	DESCRIPTION	"String"
 ::= { groupRdCfg 19778 }

vWT1ActualPowerFactor	OBJECT-TYPE
	SYNTAX	Integer32(-32768..32767)
	MAX-ACCESS	read-only
	STATUS	current
	DESCRIPTION	"DEC=3, UNIT=''"
 ::= { groupRdCfg 19779 }

vWT1ActualS	OBJECT-TYPE
	SYNTAX	Integer32(-32768..32767)
	MAX-ACCESS	read-only
	STATUS	current
	DESCRIPTION	"DEC=0, UNIT='kVA'"
 ::= { groupRdCfg 19780 }

vWT1ActualQ	OBJECT-TYPE
	SYNTAX	Integer32(-32768..32767)
	MAX-ACCESS	read-only
	STATUS	current
	DESCRIPTION	"DEC=0, UNIT='kVAr'"
 ::= { groupRdCfg 19781 }

vWT1ActualP	OBJECT-TYPE
	SYNTAX	Integer32(-32768..32767)
	MAX-ACCESS	read-only
	STATUS	current
	DESCRIPTION	"DEC=0, UNIT='kW'"
 ::= { groupRdCfg 19782 }

vWT1NominalP	OBJECT-TYPE
	SYNTAX	Integer32(0..65535)
	MAX-ACCESS	read-only
	STATUS	current
	DESCRIPTION	"DEC=0, UNIT='kW'"
 ::= { groupRdCfg 19783 }

vPV8ActualLoadCharacter	OBJECT-TYPE
	SYNTAX	DisplayString
	MAX-ACCESS	read-only
	STATUS	current
	DESCRIPTION	"String"
 ::= { groupRdCfg 19832 }

vPV8ActualPowerFactor	OBJECT-TYPE
	SYNTAX	Integer32(-32768..32767)
	MAX-ACCESS	read-only
	STATUS	current
	DESCRIPTION	"DEC=3, UNIT=''"
 ::= { groupRdCfg 19833 }

vPV8ActualS	OBJECT-TYPE
	SYNTAX	Integer32(-32768..32767)
	MAX-ACCESS	read-only
	STATUS	current
	DESCRIPTION	"DEC=0, UNIT='kVA'"
 ::= { groupRdCfg 19834 }

vPV8ActualQ	OBJECT-TYPE
	SYNTAX	Integer32(-32768..32767)
	MAX-ACCESS	read-only
	STATUS	current
	DESCRIPTION	"DEC=0, UNIT='kVAr'"
 ::= { groupRdCfg 19835 }

vPV8ActualP	OBJECT-TYPE
	SYNTAX	Integer32(-32768..32767)
	MAX-ACCESS	read-only
	STATUS	current
	DESCRIPTION	"DEC=0, UNIT='kW'"
 ::= { groupRdCfg 19836 }

vPV8NominalP	OBJECT-TYPE
	SYNTAX	Integer32(0..65535)
	MAX-ACCESS	read-only
	STATUS	current
	DESCRIPTION	"DEC=0, UNIT='kW'"
 ::= { groupRdCfg 19837 }

vPV7ActualLoadCharacter	OBJECT-TYPE
	SYNTAX	DisplayString
	MAX-ACCESS	read-only
	STATUS	current
	DESCRIPTION	"String"
 ::= { groupRdCfg 19838 }

vPV7ActualPowerFactor	OBJECT-TYPE
	SYNTAX	Integer32(-32768..32767)
	MAX-ACCESS	read-only
	STATUS	current
	DESCRIPTION	"DEC=3, UNIT=''"
 ::= { groupRdCfg 19839 }

vPV7ActualS	OBJECT-TYPE
	SYNTAX	Integer32(-32768..32767)
	MAX-ACCESS	read-only
	STATUS	current
	DESCRIPTION	"DEC=0, UNIT='kVA'"
 ::= { groupRdCfg 19840 }

vPV7ActualQ	OBJECT-TYPE
	SYNTAX	Integer32(-32768..32767)
	MAX-ACCESS	read-only
	STATUS	current
	DESCRIPTION	"DEC=0, UNIT='kVAr'"
 ::= { groupRdCfg 19841 }

vPV7ActualP	OBJECT-TYPE
	SYNTAX	Integer32(-32768..32767)
	MAX-ACCESS	read-only
	STATUS	current
	DESCRIPTION	"DEC=0, UNIT='kW'"
 ::= { groupRdCfg 19842 }

vPV7NominalP	OBJECT-TYPE
	SYNTAX	Integer32(0..65535)
	MAX-ACCESS	read-only
	STATUS	current
	DESCRIPTION	"DEC=0, UNIT='kW'"
 ::= { groupRdCfg 19843 }

vPV6ActualLoadCharacter	OBJECT-TYPE
	SYNTAX	DisplayString
	MAX-ACCESS	read-only
	STATUS	current
	DESCRIPTION	"String"
 ::= { groupRdCfg 19844 }

vPV6ActualPowerFactor	OBJECT-TYPE
	SYNTAX	Integer32(-32768..32767)
	MAX-ACCESS	read-only
	STATUS	current
	DESCRIPTION	"DEC=3, UNIT=''"
 ::= { groupRdCfg 19845 }

vPV6ActualS	OBJECT-TYPE
	SYNTAX	Integer32(-32768..32767)
	MAX-ACCESS	read-only
	STATUS	current
	DESCRIPTION	"DEC=0, UNIT='kVA'"
 ::= { groupRdCfg 19846 }

vPV6ActualQ	OBJECT-TYPE
	SYNTAX	Integer32(-32768..32767)
	MAX-ACCESS	read-only
	STATUS	current
	DESCRIPTION	"DEC=0, UNIT='kVAr'"
 ::= { groupRdCfg 19847 }

vPV6ActualP	OBJECT-TYPE
	SYNTAX	Integer32(-32768..32767)
	MAX-ACCESS	read-only
	STATUS	current
	DESCRIPTION	"DEC=0, UNIT='kW'"
 ::= { groupRdCfg 19848 }

vPV6NominalP	OBJECT-TYPE
	SYNTAX	Integer32(0..65535)
	MAX-ACCESS	read-only
	STATUS	current
	DESCRIPTION	"DEC=0, UNIT='kW'"
 ::= { groupRdCfg 19849 }

vPV5ActualLoadCharacter	OBJECT-TYPE
	SYNTAX	DisplayString
	MAX-ACCESS	read-only
	STATUS	current
	DESCRIPTION	"String"
 ::= { groupRdCfg 19850 }

vPV5ActualPowerFactor	OBJECT-TYPE
	SYNTAX	Integer32(-32768..32767)
	MAX-ACCESS	read-only
	STATUS	current
	DESCRIPTION	"DEC=3, UNIT=''"
 ::= { groupRdCfg 19851 }

vPV5ActualS	OBJECT-TYPE
	SYNTAX	Integer32(-32768..32767)
	MAX-ACCESS	read-only
	STATUS	current
	DESCRIPTION	"DEC=0, UNIT='kVA'"
 ::= { groupRdCfg 19852 }

vPV5ActualQ	OBJECT-TYPE
	SYNTAX	Integer32(-32768..32767)
	MAX-ACCESS	read-only
	STATUS	current
	DESCRIPTION	"DEC=0, UNIT='kVAr'"
 ::= { groupRdCfg 19853 }

vPV5ActualP	OBJECT-TYPE
	SYNTAX	Integer32(-32768..32767)
	MAX-ACCESS	read-only
	STATUS	current
	DESCRIPTION	"DEC=0, UNIT='kW'"
 ::= { groupRdCfg 19854 }

vPV5NominalP	OBJECT-TYPE
	SYNTAX	Integer32(0..65535)
	MAX-ACCESS	read-only
	STATUS	current
	DESCRIPTION	"DEC=0, UNIT='kW'"
 ::= { groupRdCfg 19855 }

vPV4ActualLoadCharacter	OBJECT-TYPE
	SYNTAX	DisplayString
	MAX-ACCESS	read-only
	STATUS	current
	DESCRIPTION	"String"
 ::= { groupRdCfg 19856 }

vPV4ActualPowerFactor	OBJECT-TYPE
	SYNTAX	Integer32(-32768..32767)
	MAX-ACCESS	read-only
	STATUS	current
	DESCRIPTION	"DEC=3, UNIT=''"
 ::= { groupRdCfg 19857 }

vPV4ActualS	OBJECT-TYPE
	SYNTAX	Integer32(-32768..32767)
	MAX-ACCESS	read-only
	STATUS	current
	DESCRIPTION	"DEC=0, UNIT='kVA'"
 ::= { groupRdCfg 19858 }

vPV4ActualQ	OBJECT-TYPE
	SYNTAX	Integer32(-32768..32767)
	MAX-ACCESS	read-only
	STATUS	current
	DESCRIPTION	"DEC=0, UNIT='kVAr'"
 ::= { groupRdCfg 19859 }

vPV4ActualP	OBJECT-TYPE
	SYNTAX	Integer32(-32768..32767)
	MAX-ACCESS	read-only
	STATUS	current
	DESCRIPTION	"DEC=0, UNIT='kW'"
 ::= { groupRdCfg 19860 }

vPV4NominalP	OBJECT-TYPE
	SYNTAX	Integer32(0..65535)
	MAX-ACCESS	read-only
	STATUS	current
	DESCRIPTION	"DEC=0, UNIT='kW'"
 ::= { groupRdCfg 19861 }

vPV3ActualLoadCharacter	OBJECT-TYPE
	SYNTAX	DisplayString
	MAX-ACCESS	read-only
	STATUS	current
	DESCRIPTION	"String"
 ::= { groupRdCfg 19862 }

vPV3ActualPowerFactor	OBJECT-TYPE
	SYNTAX	Integer32(-32768..32767)
	MAX-ACCESS	read-only
	STATUS	current
	DESCRIPTION	"DEC=3, UNIT=''"
 ::= { groupRdCfg 19863 }

vPV3ActualS	OBJECT-TYPE
	SYNTAX	Integer32(-32768..32767)
	MAX-ACCESS	read-only
	STATUS	current
	DESCRIPTION	"DEC=0, UNIT='kVA'"
 ::= { groupRdCfg 19864 }

vPV3ActualQ	OBJECT-TYPE
	SYNTAX	Integer32(-32768..32767)
	MAX-ACCESS	read-only
	STATUS	current
	DESCRIPTION	"DEC=0, UNIT='kVAr'"
 ::= { groupRdCfg 19865 }

vPV3ActualP	OBJECT-TYPE
	SYNTAX	Integer32(-32768..32767)
	MAX-ACCESS	read-only
	STATUS	current
	DESCRIPTION	"DEC=0, UNIT='kW'"
 ::= { groupRdCfg 19866 }

vPV3NominalP	OBJECT-TYPE
	SYNTAX	Integer32(0..65535)
	MAX-ACCESS	read-only
	STATUS	current
	DESCRIPTION	"DEC=0, UNIT='kW'"
 ::= { groupRdCfg 19867 }

vPV2ActualLoadCharacter	OBJECT-TYPE
	SYNTAX	DisplayString
	MAX-ACCESS	read-only
	STATUS	current
	DESCRIPTION	"String"
 ::= { groupRdCfg 19868 }

vPV2ActualPowerFactor	OBJECT-TYPE
	SYNTAX	Integer32(-32768..32767)
	MAX-ACCESS	read-only
	STATUS	current
	DESCRIPTION	"DEC=3, UNIT=''"
 ::= { groupRdCfg 19869 }

vPV2ActualS	OBJECT-TYPE
	SYNTAX	Integer32(-32768..32767)
	MAX-ACCESS	read-only
	STATUS	current
	DESCRIPTION	"DEC=0, UNIT='kVA'"
 ::= { groupRdCfg 19870 }

vPV2ActualQ	OBJECT-TYPE
	SYNTAX	Integer32(-32768..32767)
	MAX-ACCESS	read-only
	STATUS	current
	DESCRIPTION	"DEC=0, UNIT='kVAr'"
 ::= { groupRdCfg 19871 }

vPV2ActualP	OBJECT-TYPE
	SYNTAX	Integer32(-32768..32767)
	MAX-ACCESS	read-only
	STATUS	current
	DESCRIPTION	"DEC=0, UNIT='kW'"
 ::= { groupRdCfg 19872 }

vPV2NominalP	OBJECT-TYPE
	SYNTAX	Integer32(0..65535)
	MAX-ACCESS	read-only
	STATUS	current
	DESCRIPTION	"DEC=0, UNIT='kW'"
 ::= { groupRdCfg 19873 }

vPV1ActualLoadCharacter	OBJECT-TYPE
	SYNTAX	DisplayString
	MAX-ACCESS	read-only
	STATUS	current
	DESCRIPTION	"String"
 ::= { groupRdCfg 19874 }

vPV1ActualPowerFactor	OBJECT-TYPE
	SYNTAX	Integer32(-32768..32767)
	MAX-ACCESS	read-only
	STATUS	current
	DESCRIPTION	"DEC=3, UNIT=''"
 ::= { groupRdCfg 19875 }

vPV1ActualS	OBJECT-TYPE
	SYNTAX	Integer32(-32768..32767)
	MAX-ACCESS	read-only
	STATUS	current
	DESCRIPTION	"DEC=0, UNIT='kVA'"
 ::= { groupRdCfg 19876 }

vPV1ActualQ	OBJECT-TYPE
	SYNTAX	Integer32(-32768..32767)
	MAX-ACCESS	read-only
	STATUS	current
	DESCRIPTION	"DEC=0, UNIT='kVAr'"
 ::= { groupRdCfg 19877 }

vPV1ActualP	OBJECT-TYPE
	SYNTAX	Integer32(-32768..32767)
	MAX-ACCESS	read-only
	STATUS	current
	DESCRIPTION	"DEC=0, UNIT='kW'"
 ::= { groupRdCfg 19878 }

vPV1NominalP	OBJECT-TYPE
	SYNTAX	Integer32(0..65535)
	MAX-ACCESS	read-only
	STATUS	current
	DESCRIPTION	"DEC=0, UNIT='kW'"
 ::= { groupRdCfg 19879 }

v3PhCTLocation	OBJECT-TYPE
	SYNTAX	Integer32(0..255)
	MAX-ACCESS	read-only
	STATUS	current
	DESCRIPTION	"LIST, 0-BESS, 1-Mains"
 ::= { groupRdCfg 19886 }

vCarbonOffsetEquivalent	OBJECT-TYPE
	SYNTAX	Gauge32
	MAX-ACCESS	read-only
	STATUS	current
	DESCRIPTION	"DEC=1, UNIT='t'"
 ::= { groupRdCfg 19897 }

vHoursOfSilent	OBJECT-TYPE
	SYNTAX	Integer32
	MAX-ACCESS	read-only
	STATUS	current
	DESCRIPTION	"DEC=1, UNIT='h'"
 ::= { groupRdCfg 20130 }

vPVActualPowerFactor	OBJECT-TYPE
	SYNTAX	Integer32(-32768..32767)
	MAX-ACCESS	read-only
	STATUS	current
	DESCRIPTION	"DEC=3, UNIT=''"
 ::= { groupRdCfg 20162 }

vTotalLoadCharacter	OBJECT-TYPE
	SYNTAX	DisplayString
	MAX-ACCESS	read-only
	STATUS	current
	DESCRIPTION	"String"
 ::= { groupRdCfg 20165 }

vTotalPF	OBJECT-TYPE
	SYNTAX	Integer32(-32768..32767)
	MAX-ACCESS	read-only
	STATUS	current
	DESCRIPTION	"DEC=3, UNIT=''"
 ::= { groupRdCfg 20166 }

vTotalS	OBJECT-TYPE
	SYNTAX	Integer32
	MAX-ACCESS	read-only
	STATUS	current
	DESCRIPTION	"DEC=0, UNIT='kVA'"
 ::= { groupRdCfg 20167 }

vTotalQ	OBJECT-TYPE
	SYNTAX	Integer32
	MAX-ACCESS	read-only
	STATUS	current
	DESCRIPTION	"DEC=0, UNIT='kVAr'"
 ::= { groupRdCfg 20168 }

vTotalP	OBJECT-TYPE
	SYNTAX	Integer32
	MAX-ACCESS	read-only
	STATUS	current
	DESCRIPTION	"DEC=0, UNIT='kW'"
 ::= { groupRdCfg 20169 }

vMainsImportQMonitoring	OBJECT-TYPE
	SYNTAX	Integer32(-32768..32767)
	MAX-ACCESS	read-only
	STATUS	current
	DESCRIPTION	"DEC=0, UNIT='kVAr'"
 ::= { groupRdCfg 20171 }

vMainsImportPMonitoring	OBJECT-TYPE
	SYNTAX	Integer32(-32768..32767)
	MAX-ACCESS	read-only
	STATUS	current
	DESCRIPTION	"DEC=0, UNIT='kW'"
 ::= { groupRdCfg 20172 }

vGensetsLoadCharacter	OBJECT-TYPE
	SYNTAX	DisplayString
	MAX-ACCESS	read-only
	STATUS	current
	DESCRIPTION	"String"
 ::= { groupRdCfg 20180 }

vGensetsPowerFactor	OBJECT-TYPE
	SYNTAX	Integer32(-32768..32767)
	MAX-ACCESS	read-only
	STATUS	current
	DESCRIPTION	"DEC=3, UNIT=''"
 ::= { groupRdCfg 20181 }

vGensetsQ	OBJECT-TYPE
	SYNTAX	Integer32
	MAX-ACCESS	read-only
	STATUS	current
	DESCRIPTION	"DEC=0, UNIT='kVAr'"
 ::= { groupRdCfg 20182 }

vGensetsP	OBJECT-TYPE
	SYNTAX	Integer32
	MAX-ACCESS	read-only
	STATUS	current
	DESCRIPTION	"DEC=0, UNIT='kW'"
 ::= { groupRdCfg 20183 }

vBattCHR2EChargingCycles	OBJECT-TYPE
	SYNTAX	Gauge32
	MAX-ACCESS	read-only
	STATUS	current
	DESCRIPTION	"DEC=0, UNIT=''"
 ::= { groupRdCfg 20230 }

vMainsPowerFactorL1	OBJECT-TYPE
	SYNTAX	Integer32(-32768..32767)
	MAX-ACCESS	read-only
	STATUS	current
	DESCRIPTION	"DEC=3, UNIT=''"
 ::= { groupRdCfg 20580 }

vBESSFrequency	OBJECT-TYPE
	SYNTAX	Integer32
	MAX-ACCESS	read-only
	STATUS	current
	DESCRIPTION	"DEC=3, UNIT='Hz'"
 ::= { groupRdCfg 20799 }

vMainsCHR2FBusFrequency	OBJECT-TYPE
	SYNTAX	Integer32
	MAX-ACCESS	read-only
	STATUS	current
	DESCRIPTION	"DEC=3, UNIT='Hz'"
 ::= { groupRdCfg 20800 }

vDate	OBJECT-TYPE
	SYNTAX	OCTET STRING
	MAX-ACCESS	read-only
	STATUS	current
	DESCRIPTION	"Date"
 ::= { groupRdCfg 24553 }

vTime	OBJECT-TYPE
	SYNTAX	OCTET STRING
	MAX-ACCESS	read-only
	STATUS	current
	DESCRIPTION	"Time"
 ::= { groupRdCfg 24554 }




--******************************************************************--

conformanceGroupWrFix OBJECT-GROUP
	OBJECTS { pfActionArgument }
	STATUS  current
	DESCRIPTION  "Objects for read/write"
	::= { conformanceGroups 2 }

 pfActionArgument	OBJECT-TYPE
   SYNTAX			Gauge32
   MAX-ACCESS		read-write
   STATUS			current
   DESCRIPTION		"Command argument"
 ::= { groupWrFix 24550 }


--******************************************************************--

conformanceGroupWrCfg OBJECT-GROUP
	OBJECTS { pControllerMode }
	STATUS  current
	DESCRIPTION  "Objects for read/write"
	::= { conformanceGroups 3 }

pControllerMode	OBJECT-TYPE
	SYNTAX	Integer32(0..255)
	MAX-ACCESS	read-write
	STATUS	current
	DESCRIPTION	"LIST, 0-OFF, 1-MAN, 2-AUTO"
 ::= { groupWrCfg 8315 }




--******************************************************************--

conformanceGroupW OBJECT-GROUP
	OBJECTS { pfPassword, pfActionCommand }
	STATUS  current
	DESCRIPTION  "Objects for writing only"
	::= { conformanceGroups 4 }

pfActionCommand	OBJECT-TYPE
   SYNTAX		Integer32(0..65535)
   MAX-ACCESS	read-write
   STATUS		current
   DESCRIPTION	"Command"
 ::= { groupW 24551 }


--******************************************************************--

conformanceGroupNotifData OBJECT-GROUP
	OBJECTS { tControllerName, tSerNum, tTrapText }
	STATUS  current
	DESCRIPTION  "Objects for trap bindings, not accessible"
	::= { conformanceGroups 5 }

tControllerName	OBJECT-TYPE
	SYNTAX		DisplayString
	MAX-ACCESS	accessible-for-notify
	STATUS		current
	DESCRIPTION	"Name of the controller."
 ::= { notificationData 1 }

tSerNum			OBJECT-TYPE
    SYNTAX		DisplayString
    MAX-ACCESS	accessible-for-notify
    STATUS		current
    DESCRIPTION	"Serial number of the controller."
 ::= { notificationData 2 }

tTrapText		OBJECT-TYPE
    SYNTAX		DisplayString
    MAX-ACCESS	accessible-for-notify
    STATUS		current
    DESCRIPTION	"Trap reason description."
 ::= { notificationData 3 }


--******************************************************************--

conformanceGroupNotifications NOTIFICATION-GROUP
	NOTIFICATIONS { tMCBFeedbackL1Activated, tMCBFeedbackL1Disappeared, tMCBFeedbackL1AlarmReset, tMCBFeedbackL2Activated, tMCBFeedbackL2Disappeared,
tMCBFeedbackL2AlarmReset, tMCBFeedbackSFActivated, tMCBFeedbackSFDisappeared, tMCBFeedbackSFAlarmReset, tBESSReadyToLoadL1Activated,
tBESSReadyToLoadL1Disappeared, tBESSReadyToLoadL1AlarmReset, tBESSReadyToLoadL2Activated, tBESSReadyToLoadL2Disappeared, tBESSReadyToLoadL2AlarmReset,
tBESSReadyToLoadSFActivated, tBESSReadyToLoadSFDisappeared, tBESSReadyToLoadSFAlarmReset, tPVCBFeedbackL1Activated, tPVCBFeedbackL1Disappeared,
tPVCBFeedbackL1AlarmReset, tPVCBFeedbackL2Activated, tPVCBFeedbackL2Disappeared, tPVCBFeedbackL2AlarmReset, tPVCBFeedbackSFActivated,
tPVCBFeedbackSFDisappeared, tPVCBFeedbackSFAlarmReset, tRemoteOFFL1Activated, tRemoteOFFL1Disappeared, tRemoteOFFL1AlarmReset,
tRemoteOFFL2Activated, tRemoteOFFL2Disappeared, tRemoteOFFL2AlarmReset, tRemoteOFFSFActivated, tRemoteOFFSFDisappeared,
tRemoteOFFSFAlarmReset, tPrechargeFinishedL1Activated, tPrechargeFinishedL1Disappeared, tPrechargeFinishedL1AlarmReset, tPrechargeFinishedL2Activated,
tPrechargeFinishedL2Disappeared, tPrechargeFinishedL2AlarmReset, tPrechargeFinishedSFActivated, tPrechargeFinishedSFDisappeared, tPrechargeFinishedSFAlarmReset,
tSdOverrideL1Activated, tSdOverrideL1Disappeared, tSdOverrideL1AlarmReset, tSdOverrideL2Activated, tSdOverrideL2Disappeared,
tSdOverrideL2AlarmReset, tSdOverrideSFActivated, tSdOverrideSFDisappeared, tSdOverrideSFAlarmReset, tVSGModeOnL1Activated,
tVSGModeOnL1Disappeared, tVSGModeOnL1AlarmReset, tVSGModeOnL2Activated, tVSGModeOnL2Disappeared, tVSGModeOnL2AlarmReset,
tVSGModeOnSFActivated, tVSGModeOnSFDisappeared, tVSGModeOnSFAlarmReset, tOnOffStatusesL1Activated, tOnOffStatusesL1Disappeared,
tOnOffStatusesL1AlarmReset, tOnOffStatusesL2Activated, tOnOffStatusesL2Disappeared, tOnOffStatusesL2AlarmReset, tOnOffStatusesSFActivated,
tOnOffStatusesSFDisappeared, tOnOffStatusesSFAlarmReset, tFaultStatusL1Activated, tFaultStatusL1Disappeared, tFaultStatusL1AlarmReset,
tFaultStatusL2Activated, tFaultStatusL2Disappeared, tFaultStatusL2AlarmReset, tFaultStatusSFActivated, tFaultStatusSFDisappeared,
tFaultStatusSFAlarmReset, tCUAIN01L1Activated, tCUAIN01L1Disappeared, tCUAIN01L1AlarmReset, tCUAIN01L2Activated,
tCUAIN01L2Disappeared, tCUAIN01L2AlarmReset, tCUAIN01SFActivated, tCUAIN01SFDisappeared, tCUAIN01SFAlarmReset,
tActivePowerL1Activated1, tActivePowerL1Disappeared1, tActivePowerL1AlarmReset1, tActivePowerL2Activated1, tActivePowerL2Disappeared1,
tActivePowerL2AlarmReset1, tActivePowerSFActivated1, tActivePowerSFDisappeared1, tActivePowerSFAlarmReset1, tReactivePowerL1Activated1,
tReactivePowerL1Disappeared1, tReactivePowerL1AlarmReset1, tReactivePowerL2Activated1, tReactivePowerL2Disappeared1, tReactivePowerL2AlarmReset1,
tReactivePowerSFActivated1, tReactivePowerSFDisappeared1, tReactivePowerSFAlarmReset1, tNominalActivePowerL1Activated, tNominalActivePowerL1Disappeared,
tNominalActivePowerL1AlarmReset, tNominalActivePowerL2Activated, tNominalActivePowerL2Disappeared, tNominalActivePowerL2AlarmReset, tNominalActivePowerSFActivated,
tNominalActivePowerSFDisappeared, tNominalActivePowerSFAlarmReset, tMaximumActivePowerL1Activated, tMaximumActivePowerL1Disappeared, tMaximumActivePowerL1AlarmReset,
tMaximumActivePowerL2Activated, tMaximumActivePowerL2Disappeared, tMaximumActivePowerL2AlarmReset, tMaximumActivePowerSFActivated, tMaximumActivePowerSFDisappeared,
tMaximumActivePowerSFAlarmReset, tMaximumApparentPowerL1Activated, tMaximumApparentPowerL1Disappeared, tMaximumApparentPowerL1AlarmReset, tMaximumApparentPowerL2Activated,
tMaximumApparentPowerL2Disappeared, tMaximumApparentPowerL2AlarmReset, tMaximumApparentPowerSFActivated, tMaximumApparentPowerSFDisappeared, tMaximumApparentPowerSFAlarmReset,
tInputPowerL1Activated, tInputPowerL1Disappeared, tInputPowerL1AlarmReset, tInputPowerL2Activated, tInputPowerL2Disappeared,
tInputPowerL2AlarmReset, tInputPowerSFActivated, tInputPowerSFDisappeared, tInputPowerSFAlarmReset, tActivePowerL1Activated2,
tActivePowerL1Disappeared2, tActivePowerL1AlarmReset2, tActivePowerL2Activated2, tActivePowerL2Disappeared2, tActivePowerL2AlarmReset2,
tActivePowerSFActivated2, tActivePowerSFDisappeared2, tActivePowerSFAlarmReset2, tReactivePowerL1Activated2, tReactivePowerL1Disappeared2,
tReactivePowerL1AlarmReset2, tReactivePowerL2Activated2, tReactivePowerL2Disappeared2, tReactivePowerL2AlarmReset2, tReactivePowerSFActivated2,
tReactivePowerSFDisappeared2, tReactivePowerSFAlarmReset2, tRealTimeActivePowerPercentL1Activated, tRealTimeActivePowerPercentL1Disappeared, tRealTimeActivePowerPercentL1AlarmReset,
tRealTimeActivePowerPercentL2Activated, tRealTimeActivePowerPercentL2Disappeared, tRealTimeActivePowerPercentL2AlarmReset, tRealTimeActivePowerPercentSFActivated, tRealTimeActivePowerPercentSFDisappeared,
tRealTimeActivePowerPercentSFAlarmReset, tREACTPercentL1Activated1, tREACTPercentL1Disappeared1, tREACTPercentL1AlarmReset1, tREACTPercentL2Activated1,
tREACTPercentL2Disappeared1, tREACTPercentL2AlarmReset1, tREACTPercentSFActivated1, tREACTPercentSFDisappeared1, tREACTPercentSFAlarmReset1,
tPFSETL1Activated, tPFSETL1Disappeared, tPFSETL1AlarmReset, tPFSETL2Activated, tPFSETL2Disappeared,
tPFSETL2AlarmReset, tPFSETSFActivated, tPFSETSFDisappeared, tPFSETSFAlarmReset, tTOTKWhPV2L1Activated,
tTOTKWhPV2L1Disappeared, tTOTKWhPV2L1AlarmReset, tTOTKWhPV2L2Activated, tTOTKWhPV2L2Disappeared, tTOTKWhPV2L2AlarmReset,
tTOTKWhPV2SFActivated, tTOTKWhPV2SFDisappeared, tTOTKWhPV2SFAlarmReset, tTOTKWhPV1L1Activated, tTOTKWhPV1L1Disappeared,
tTOTKWhPV1L1AlarmReset, tTOTKWhPV1L2Activated, tTOTKWhPV1L2Disappeared, tTOTKWhPV1L2AlarmReset, tTOTKWhPV1SFActivated,
tTOTKWhPV1SFDisappeared, tTOTKWhPV1SFAlarmReset, tACTPOWERL1Activated, tACTPOWERL1Disappeared, tACTPOWERL1AlarmReset,
tACTPOWERL2Activated, tACTPOWERL2Disappeared, tACTPOWERL2AlarmReset, tACTPOWERSFActivated, tACTPOWERSFDisappeared,
tACTPOWERSFAlarmReset, tREACTPercentL1Activated2, tREACTPercentL1Disappeared2, tREACTPercentL1AlarmReset2, tREACTPercentL2Activated2,
tREACTPercentL2Disappeared2, tREACTPercentL2AlarmReset2, tREACTPercentSFActivated2, tREACTPercentSFDisappeared2, tREACTPercentSFAlarmReset2,
tREACTPOWERL1Activated, tREACTPOWERL1Disappeared, tREACTPOWERL1AlarmReset, tREACTPOWERL2Activated, tREACTPOWERL2Disappeared,
tREACTPOWERL2AlarmReset, tREACTPOWERSFActivated, tREACTPOWERSFDisappeared, tREACTPOWERSFAlarmReset, tACTNRJIMPORTL1Activated,
tACTNRJIMPORTL1Disappeared, tACTNRJIMPORTL1AlarmReset, tACTNRJIMPORTL2Activated, tACTNRJIMPORTL2Disappeared, tACTNRJIMPORTL2AlarmReset,
tACTNRJIMPORTSFActivated, tACTNRJIMPORTSFDisappeared, tACTNRJIMPORTSFAlarmReset, tACTNRJEXPORTL1Activated, tACTNRJEXPORTL1Disappeared,
tACTNRJEXPORTL1AlarmReset, tACTNRJEXPORTL2Activated, tACTNRJEXPORTL2Disappeared, tACTNRJEXPORTL2AlarmReset, tACTNRJEXPORTSFActivated,
tACTNRJEXPORTSFDisappeared, tACTNRJEXPORTSFAlarmReset, tAbsorbedEnergyL1Activated, tAbsorbedEnergyL1Disappeared, tAbsorbedEnergyL1AlarmReset,
tAbsorbedEnergyL2Activated, tAbsorbedEnergyL2Disappeared, tAbsorbedEnergyL2AlarmReset, tAbsorbedEnergySFActivated, tAbsorbedEnergySFDisappeared,
tAbsorbedEnergySFAlarmReset, tReleasedEnergyL1Activated, tReleasedEnergyL1Disappeared, tReleasedEnergyL1AlarmReset, tReleasedEnergyL2Activated,
tReleasedEnergyL2Disappeared, tReleasedEnergyL2AlarmReset, tReleasedEnergySFActivated, tReleasedEnergySFDisappeared, tReleasedEnergySFAlarmReset,
tSOCL1Activated, tSOCL1Disappeared, tSOCL1AlarmReset, tSOCL2Activated, tSOCL2Disappeared,
tSOCL2AlarmReset, tSOCSFActivated, tSOCSFDisappeared, tSOCSFAlarmReset, tSOHL1Activated,
tSOHL1Disappeared, tSOHL1AlarmReset, tSOHL2Activated, tSOHL2Disappeared, tSOHL2AlarmReset,
tSOHSFActivated, tSOHSFDisappeared, tSOHSFAlarmReset, tCurrentL1L1Activated, tCurrentL1L1Disappeared,
tCurrentL1L1AlarmReset, tCurrentL1L2Activated, tCurrentL1L2Disappeared, tCurrentL1L2AlarmReset, tCurrentL1SFActivated,
tCurrentL1SFDisappeared, tCurrentL1SFAlarmReset, tCurrentL2L1Activated, tCurrentL2L1Disappeared, tCurrentL2L1AlarmReset,
tCurrentL2L2Activated, tCurrentL2L2Disappeared, tCurrentL2L2AlarmReset, tCurrentL2SFActivated, tCurrentL2SFDisappeared,
tCurrentL2SFAlarmReset, tCurrentL3L1Activated, tCurrentL3L1Disappeared, tCurrentL3L1AlarmReset, tCurrentL3L2Activated,
tCurrentL3L2Disappeared, tCurrentL3L2AlarmReset, tCurrentL3SFActivated, tCurrentL3SFDisappeared, tCurrentL3SFAlarmReset,
tActivePowerL1Activated3, tActivePowerL1Disappeared3, tActivePowerL1AlarmReset3, tActivePowerL2Activated3, tActivePowerL2Disappeared3,
tActivePowerL2AlarmReset3, tActivePowerSFActivated3, tActivePowerSFDisappeared3, tActivePowerSFAlarmReset3, tGridVoltageL1L2L1Activated,
tGridVoltageL1L2L1Disappeared, tGridVoltageL1L2L1AlarmReset, tGridVoltageL1L2L2Activated, tGridVoltageL1L2L2Disappeared, tGridVoltageL1L2L2AlarmReset,
tGridVoltageL1L2SFActivated, tGridVoltageL1L2SFDisappeared, tGridVoltageL1L2SFAlarmReset, tGridVoltageL2L3L1Activated, tGridVoltageL2L3L1Disappeared,
tGridVoltageL2L3L1AlarmReset, tGridVoltageL2L3L2Activated, tGridVoltageL2L3L2Disappeared, tGridVoltageL2L3L2AlarmReset, tGridVoltageL2L3SFActivated,
tGridVoltageL2L3SFDisappeared, tGridVoltageL2L3SFAlarmReset, tGridVoltageL3L1L1Activated, tGridVoltageL3L1L1Disappeared, tGridVoltageL3L1L1AlarmReset,
tGridVoltageL3L1L2Activated, tGridVoltageL3L1L2Disappeared, tGridVoltageL3L1L2AlarmReset, tGridVoltageL3L1SFActivated, tGridVoltageL3L1SFDisappeared,
tGridVoltageL3L1SFAlarmReset, tGridFrequencyL1Activated, tGridFrequencyL1Disappeared, tGridFrequencyL1AlarmReset, tGridFrequencyL2Activated,
tGridFrequencyL2Disappeared, tGridFrequencyL2AlarmReset, tGridFrequencySFActivated, tGridFrequencySFDisappeared, tGridFrequencySFAlarmReset,
tReactivePowerL1Activated3, tReactivePowerL1Disappeared3, tReactivePowerL1AlarmReset3, tReactivePowerL2Activated3, tReactivePowerL2Disappeared3,
tReactivePowerL2AlarmReset3, tReactivePowerSFActivated3, tReactivePowerSFDisappeared3, tReactivePowerSFAlarmReset3, tEmergencyStopL2Activated,
tEmergencyStopL2Disappeared, tEmergencyStopL2AlarmReset, tBESSVoltageL1NL1Activated, tBESSVoltageL1NL1Disappeared, tBESSVoltageL1NL1AlarmReset,
tBESSVoltageL1NL2Activated, tBESSVoltageL1NL2Disappeared, tBESSVoltageL1NL2AlarmReset, tBESSVoltageL1NSFActivated, tBESSVoltageL1NSFDisappeared,
tBESSVoltageL1NSFAlarmReset, tBESSVoltageL2NL1Activated, tBESSVoltageL2NL1Disappeared, tBESSVoltageL2NL1AlarmReset, tBESSVoltageL2NL2Activated,
tBESSVoltageL2NL2Disappeared, tBESSVoltageL2NL2AlarmReset, tBESSVoltageL2NSFActivated, tBESSVoltageL2NSFDisappeared, tBESSVoltageL2NSFAlarmReset,
tBESSVoltageL3NL1Activated, tBESSVoltageL3NL1Disappeared, tBESSVoltageL3NL1AlarmReset, tBESSVoltageL3NL2Activated, tBESSVoltageL3NL2Disappeared,
tBESSVoltageL3NL2AlarmReset, tBESSVoltageL3NSFActivated, tBESSVoltageL3NSFDisappeared, tBESSVoltageL3NSFAlarmReset, tBESSVoltageL1L2L1Activated,
tBESSVoltageL1L2L1Disappeared, tBESSVoltageL1L2L1AlarmReset, tBESSVoltageL1L2L2Activated, tBESSVoltageL1L2L2Disappeared, tBESSVoltageL1L2L2AlarmReset,
tBESSVoltageL1L2SFActivated, tBESSVoltageL1L2SFDisappeared, tBESSVoltageL1L2SFAlarmReset, tBESSVoltageL2L3L1Activated, tBESSVoltageL2L3L1Disappeared,
tBESSVoltageL2L3L1AlarmReset, tBESSVoltageL2L3L2Activated, tBESSVoltageL2L3L2Disappeared, tBESSVoltageL2L3L2AlarmReset, tBESSVoltageL2L3SFActivated,
tBESSVoltageL2L3SFDisappeared, tBESSVoltageL2L3SFAlarmReset, tBESSVoltageL3L1L1Activated, tBESSVoltageL3L1L1Disappeared, tBESSVoltageL3L1L1AlarmReset,
tBESSVoltageL3L1L2Activated, tBESSVoltageL3L1L2Disappeared, tBESSVoltageL3L1L2AlarmReset, tBESSVoltageL3L1SFActivated, tBESSVoltageL3L1SFDisappeared,
tBESSVoltageL3L1SFAlarmReset, tBESSFrequencyL1Activated, tBESSFrequencyL1Disappeared, tBESSFrequencyL1AlarmReset, tBESSFrequencyL2Activated,
tBESSFrequencyL2Disappeared, tBESSFrequencyL2AlarmReset, tBESSFrequencySFActivated, tBESSFrequencySFDisappeared, tBESSFrequencySFAlarmReset,
tMainsCHR2FBusVoltageL1NL1Activated, tMainsCHR2FBusVoltageL1NL1Disappeared, tMainsCHR2FBusVoltageL1NL1AlarmReset, tMainsCHR2FBusVoltageL1NL2Activated, tMainsCHR2FBusVoltageL1NL2Disappeared,
tMainsCHR2FBusVoltageL1NL2AlarmReset, tMainsCHR2FBusVoltageL1NSFActivated, tMainsCHR2FBusVoltageL1NSFDisappeared, tMainsCHR2FBusVoltageL1NSFAlarmReset, tMainsCHR2FBusVoltageL2NL1Activated,
tMainsCHR2FBusVoltageL2NL1Disappeared, tMainsCHR2FBusVoltageL2NL1AlarmReset, tMainsCHR2FBusVoltageL2NL2Activated, tMainsCHR2FBusVoltageL2NL2Disappeared, tMainsCHR2FBusVoltageL2NL2AlarmReset,
tMainsCHR2FBusVoltageL2NSFActivated, tMainsCHR2FBusVoltageL2NSFDisappeared, tMainsCHR2FBusVoltageL2NSFAlarmReset, tMainsCHR2FBusVoltageL3NL1Activated, tMainsCHR2FBusVoltageL3NL1Disappeared,
tMainsCHR2FBusVoltageL3NL1AlarmReset, tMainsCHR2FBusVoltageL3NL2Activated, tMainsCHR2FBusVoltageL3NL2Disappeared, tMainsCHR2FBusVoltageL3NL2AlarmReset, tMainsCHR2FBusVoltageL3NSFActivated,
tMainsCHR2FBusVoltageL3NSFDisappeared, tMainsCHR2FBusVoltageL3NSFAlarmReset, tMainsCHR2FBusVoltageL1L2L1Activated, tMainsCHR2FBusVoltageL1L2L1Disappeared, tMainsCHR2FBusVoltageL1L2L1AlarmReset,
tMainsCHR2FBusVoltageL1L2L2Activated, tMainsCHR2FBusVoltageL1L2L2Disappeared, tMainsCHR2FBusVoltageL1L2L2AlarmReset, tMainsCHR2FBusVoltageL1L2SFActivated, tMainsCHR2FBusVoltageL1L2SFDisappeared,
tMainsCHR2FBusVoltageL1L2SFAlarmReset, tMainsCHR2FBusVoltageL2L3L1Activated, tMainsCHR2FBusVoltageL2L3L1Disappeared, tMainsCHR2FBusVoltageL2L3L1AlarmReset, tMainsCHR2FBusVoltageL2L3L2Activated,
tMainsCHR2FBusVoltageL2L3L2Disappeared, tMainsCHR2FBusVoltageL2L3L2AlarmReset, tMainsCHR2FBusVoltageL2L3SFActivated, tMainsCHR2FBusVoltageL2L3SFDisappeared, tMainsCHR2FBusVoltageL2L3SFAlarmReset,
tMainsCHR2FBusVoltageL3L1L1Activated, tMainsCHR2FBusVoltageL3L1L1Disappeared, tMainsCHR2FBusVoltageL3L1L1AlarmReset, tMainsCHR2FBusVoltageL3L1L2Activated, tMainsCHR2FBusVoltageL3L1L2Disappeared,
tMainsCHR2FBusVoltageL3L1L2AlarmReset, tMainsCHR2FBusVoltageL3L1SFActivated, tMainsCHR2FBusVoltageL3L1SFDisappeared, tMainsCHR2FBusVoltageL3L1SFAlarmReset, tMainsCHR2FBusFrequencyL1Activated,
tMainsCHR2FBusFrequencyL1Disappeared, tMainsCHR2FBusFrequencyL1AlarmReset, tMainsCHR2FBusFrequencyL2Activated, tMainsCHR2FBusFrequencyL2Disappeared, tMainsCHR2FBusFrequencyL2AlarmReset,
tMainsCHR2FBusFrequencySFActivated, tMainsCHR2FBusFrequencySFDisappeared, tMainsCHR2FBusFrequencySFAlarmReset, tMainsCHR2FBusVUnbalancePhNL1Activated, tMainsCHR2FBusVUnbalancePhNL1Disappeared,
tMainsCHR2FBusVUnbalancePhNL1AlarmReset, tMainsCHR2FBusVUnbalancePhNL2Activated1, tMainsCHR2FBusVUnbalancePhNL2Disappeared1, tMainsCHR2FBusVUnbalancePhNL2AlarmReset1, tMainsCHR2FBusVUnbalancePhNSFActivated,
tMainsCHR2FBusVUnbalancePhNSFDisappeared, tMainsCHR2FBusVUnbalancePhNSFAlarmReset, tMainsCHR2FBusVUnbalancePhPhL1Activated, tMainsCHR2FBusVUnbalancePhPhL1Disappeared, tMainsCHR2FBusVUnbalancePhPhL1AlarmReset,
tMainsCHR2FBusVUnbalancePhPhL2Activated1, tMainsCHR2FBusVUnbalancePhPhL2Disappeared1, tMainsCHR2FBusVUnbalancePhPhL2AlarmReset1, tMainsCHR2FBusVUnbalancePhPhSFActivated, tMainsCHR2FBusVUnbalancePhPhSFDisappeared,
tMainsCHR2FBusVUnbalancePhPhSFAlarmReset, tBESSVUnbalancePhPhL1Activated, tBESSVUnbalancePhPhL1Disappeared, tBESSVUnbalancePhPhL1AlarmReset, tBESSVUnbalancePhPhL2Activated1,
tBESSVUnbalancePhPhL2Disappeared1, tBESSVUnbalancePhPhL2AlarmReset1, tBESSVUnbalancePhPhSFActivated, tBESSVUnbalancePhPhSFDisappeared, tBESSVUnbalancePhPhSFAlarmReset,
tBESSVUnbalancePhNL1Activated, tBESSVUnbalancePhNL1Disappeared, tBESSVUnbalancePhNL1AlarmReset, tBESSVUnbalancePhNL2Activated1, tBESSVUnbalancePhNL2Disappeared1,
tBESSVUnbalancePhNL2AlarmReset1, tBESSVUnbalancePhNSFActivated, tBESSVUnbalancePhNSFDisappeared, tBESSVUnbalancePhNSFAlarmReset, tBESSCurrentUnbalanceL1Activated,
tBESSCurrentUnbalanceL1Disappeared, tBESSCurrentUnbalanceL1AlarmReset, tBESSCurrentUnbalanceL2Activated1, tBESSCurrentUnbalanceL2Disappeared1, tBESSCurrentUnbalanceL2AlarmReset1,
tBESSCurrentUnbalanceSFActivated, tBESSCurrentUnbalanceSFDisappeared, tBESSCurrentUnbalanceSFAlarmReset, tMainsCHR2FBusGtVL1NL2Activated, tMainsCHR2FBusGtVL1NL2Disappeared,
tMainsCHR2FBusGtVL1NL2AlarmReset, tMainsCHR2FBusLtVL1NL2Activated, tMainsCHR2FBusLtVL1NL2Disappeared, tMainsCHR2FBusLtVL1NL2AlarmReset, tMainsCHR2FBusGtVL2NL2Activated,
tMainsCHR2FBusGtVL2NL2Disappeared, tMainsCHR2FBusGtVL2NL2AlarmReset, tMainsCHR2FBusLtVL2NL2Activated, tMainsCHR2FBusLtVL2NL2Disappeared, tMainsCHR2FBusLtVL2NL2AlarmReset,
tMainsCHR2FBusGtVL3NL2Activated, tMainsCHR2FBusGtVL3NL2Disappeared, tMainsCHR2FBusGtVL3NL2AlarmReset, tMainsCHR2FBusLtVL3NL2Activated, tMainsCHR2FBusLtVL3NL2Disappeared,
tMainsCHR2FBusLtVL3NL2AlarmReset, tMainsCHR2FBusGtVL1L2L2Activated, tMainsCHR2FBusGtVL1L2L2Disappeared, tMainsCHR2FBusGtVL1L2L2AlarmReset, tMainsCHR2FBusLtVL1L2L2Activated,
tMainsCHR2FBusLtVL1L2L2Disappeared, tMainsCHR2FBusLtVL1L2L2AlarmReset, tMainsCHR2FBusGtVL2L3L2Activated, tMainsCHR2FBusGtVL2L3L2Disappeared, tMainsCHR2FBusGtVL2L3L2AlarmReset,
tMainsCHR2FBusLtVL2L3L2Activated, tMainsCHR2FBusLtVL2L3L2Disappeared, tMainsCHR2FBusLtVL2L3L2AlarmReset, tMainsCHR2FBusGtVL3L1L2Activated, tMainsCHR2FBusGtVL3L1L2Disappeared,
tMainsCHR2FBusGtVL3L1L2AlarmReset, tMainsCHR2FBusLtVL3L1L2Activated, tMainsCHR2FBusLtVL3L1L2Disappeared, tMainsCHR2FBusLtVL3L1L2AlarmReset, tMainsCHR2FBusGtGtVL1NL2Activated,
tMainsCHR2FBusGtGtVL1NL2Disappeared, tMainsCHR2FBusGtGtVL1NL2AlarmReset, tMainsCHR2FBusLtLtVL1NL2Activated, tMainsCHR2FBusLtLtVL1NL2Disappeared, tMainsCHR2FBusLtLtVL1NL2AlarmReset,
tMainsCHR2FBusGtGtVL2NL2Activated, tMainsCHR2FBusGtGtVL2NL2Disappeared, tMainsCHR2FBusGtGtVL2NL2AlarmReset, tMainsCHR2FBusLtLtVL2NL2Activated, tMainsCHR2FBusLtLtVL2NL2Disappeared,
tMainsCHR2FBusLtLtVL2NL2AlarmReset, tMainsCHR2FBusGtGtVL3NL2Activated, tMainsCHR2FBusGtGtVL3NL2Disappeared, tMainsCHR2FBusGtGtVL3NL2AlarmReset, tMainsCHR2FBusLtLtVL3NL2Activated,
tMainsCHR2FBusLtLtVL3NL2Disappeared, tMainsCHR2FBusLtLtVL3NL2AlarmReset, tMainsCHR2FBusGtGtVL1L2L2Activated, tMainsCHR2FBusGtGtVL1L2L2Disappeared, tMainsCHR2FBusGtGtVL1L2L2AlarmReset,
tMainsCHR2FBusLtLtVL1L2L2Activated, tMainsCHR2FBusLtLtVL1L2L2Disappeared, tMainsCHR2FBusLtLtVL1L2L2AlarmReset, tMainsCHR2FBusGtGtVL2L3L2Activated, tMainsCHR2FBusGtGtVL2L3L2Disappeared,
tMainsCHR2FBusGtGtVL2L3L2AlarmReset, tMainsCHR2FBusLtLtVL2L3L2Activated, tMainsCHR2FBusLtLtVL2L3L2Disappeared, tMainsCHR2FBusLtLtVL2L3L2AlarmReset, tMainsCHR2FBusGtGtVL3L1L2Activated,
tMainsCHR2FBusGtGtVL3L1L2Disappeared, tMainsCHR2FBusGtGtVL3L1L2AlarmReset, tMainsCHR2FBusLtLtVL3L1L2Activated, tMainsCHR2FBusLtLtVL3L1L2Disappeared, tMainsCHR2FBusLtLtVL3L1L2AlarmReset,
tMainsCHR2FBus10minAvgGtVL1NL2Activated, tMainsCHR2FBus10minAvgGtVL1NL2Disappeared, tMainsCHR2FBus10minAvgGtVL1NL2AlarmReset, tMainsCHR2FBus10minAvgGtVL2NL2Activated, tMainsCHR2FBus10minAvgGtVL2NL2Disappeared,
tMainsCHR2FBus10minAvgGtVL2NL2AlarmReset, tMainsCHR2FBus10minAvgGtVL3NL2Activated, tMainsCHR2FBus10minAvgGtVL3NL2Disappeared, tMainsCHR2FBus10minAvgGtVL3NL2AlarmReset, tMainsCHR2FBus10minAvgGtVL1L2L2Activated,
tMainsCHR2FBus10minAvgGtVL1L2L2Disappeared, tMainsCHR2FBus10minAvgGtVL1L2L2AlarmReset, tMainsCHR2FBus10minAvgGtVL2L3L2Activated, tMainsCHR2FBus10minAvgGtVL2L3L2Disappeared, tMainsCHR2FBus10minAvgGtVL2L3L2AlarmReset,
tMainsCHR2FBus10minAvgGtVL3L1L2Activated, tMainsCHR2FBus10minAvgGtVL3L1L2Disappeared, tMainsCHR2FBus10minAvgGtVL3L1L2AlarmReset, tMainsCHR2FBusVUnbalancePhPhL2Activated2, tMainsCHR2FBusVUnbalancePhPhL2Disappeared2,
tMainsCHR2FBusVUnbalancePhPhL2AlarmReset2, tMainsCHR2FBusVUnbalancePhNL2Activated2, tMainsCHR2FBusVUnbalancePhNL2Disappeared2, tMainsCHR2FBusVUnbalancePhNL2AlarmReset2, tMainsCHR2FBusGtFL2Activated,
tMainsCHR2FBusGtFL2Disappeared, tMainsCHR2FBusGtFL2AlarmReset, tMainsCHR2FBusLtFL2Activated, tMainsCHR2FBusLtFL2Disappeared, tMainsCHR2FBusLtFL2AlarmReset,
tMainsCHR2FBusGtGtFL2Activated, tMainsCHR2FBusGtGtFL2Disappeared, tMainsCHR2FBusGtGtFL2AlarmReset, tMainsCHR2FBusLtLtFL2Activated, tMainsCHR2FBusLtLtFL2Disappeared,
tMainsCHR2FBusLtLtFL2AlarmReset, tVRTUm1OVRTL1Activated, tVRTUm1OVRTL1Disappeared, tVRTUm1OVRTL1AlarmReset, tVRTUm1OVRTL2Activated,
tVRTUm1OVRTL2Disappeared, tVRTUm1OVRTL2AlarmReset, tVRTUm1OVRTSFActivated, tVRTUm1OVRTSFDisappeared, tVRTUm1OVRTSFAlarmReset,
tVRTUm1LVRT1L1Activated, tVRTUm1LVRT1L1Disappeared, tVRTUm1LVRT1L1AlarmReset, tVRTUm1LVRT1L2Activated, tVRTUm1LVRT1L2Disappeared,
tVRTUm1LVRT1L2AlarmReset, tVRTUm1LVRT1SFActivated, tVRTUm1LVRT1SFDisappeared, tVRTUm1LVRT1SFAlarmReset, tVRTUm1LVRT2L1Activated,
tVRTUm1LVRT2L1Disappeared, tVRTUm1LVRT2L1AlarmReset, tVRTUm1LVRT2L2Activated, tVRTUm1LVRT2L2Disappeared, tVRTUm1LVRT2L2AlarmReset,
tVRTUm1LVRT2SFActivated, tVRTUm1LVRT2SFDisappeared, tVRTUm1LVRT2SFAlarmReset, tVRTUm1LVRT3L1Activated, tVRTUm1LVRT3L1Disappeared,
tVRTUm1LVRT3L1AlarmReset, tVRTUm1LVRT3L2Activated, tVRTUm1LVRT3L2Disappeared, tVRTUm1LVRT3L2AlarmReset, tVRTUm1LVRT3SFActivated,
tVRTUm1LVRT3SFDisappeared, tVRTUm1LVRT3SFAlarmReset, tVRTUm2OVRTL1Activated, tVRTUm2OVRTL1Disappeared, tVRTUm2OVRTL1AlarmReset,
tVRTUm2OVRTL2Activated, tVRTUm2OVRTL2Disappeared, tVRTUm2OVRTL2AlarmReset, tVRTUm2OVRTSFActivated, tVRTUm2OVRTSFDisappeared,
tVRTUm2OVRTSFAlarmReset, tVRTUm2LVRT1L1Activated, tVRTUm2LVRT1L1Disappeared, tVRTUm2LVRT1L1AlarmReset, tVRTUm2LVRT1L2Activated,
tVRTUm2LVRT1L2Disappeared, tVRTUm2LVRT1L2AlarmReset, tVRTUm2LVRT1SFActivated, tVRTUm2LVRT1SFDisappeared, tVRTUm2LVRT1SFAlarmReset,
tVRTUm2LVRT2L1Activated, tVRTUm2LVRT2L1Disappeared, tVRTUm2LVRT2L1AlarmReset, tVRTUm2LVRT2L2Activated, tVRTUm2LVRT2L2Disappeared,
tVRTUm2LVRT2L2AlarmReset, tVRTUm2LVRT2SFActivated, tVRTUm2LVRT2SFDisappeared, tVRTUm2LVRT2SFAlarmReset, tVRTUm2LVRT3L1Activated,
tVRTUm2LVRT3L1Disappeared, tVRTUm2LVRT3L1AlarmReset, tVRTUm2LVRT3L2Activated, tVRTUm2LVRT3L2Disappeared, tVRTUm2LVRT3L2AlarmReset,
tVRTUm2LVRT3SFActivated, tVRTUm2LVRT3SFDisappeared, tVRTUm2LVRT3SFAlarmReset, tVRTUm3OVRTL1Activated, tVRTUm3OVRTL1Disappeared,
tVRTUm3OVRTL1AlarmReset, tVRTUm3OVRTL2Activated, tVRTUm3OVRTL2Disappeared, tVRTUm3OVRTL2AlarmReset, tVRTUm3OVRTSFActivated,
tVRTUm3OVRTSFDisappeared, tVRTUm3OVRTSFAlarmReset, tVRTUm3LVRT1L1Activated, tVRTUm3LVRT1L1Disappeared, tVRTUm3LVRT1L1AlarmReset,
tVRTUm3LVRT1L2Activated, tVRTUm3LVRT1L2Disappeared, tVRTUm3LVRT1L2AlarmReset, tVRTUm3LVRT1SFActivated, tVRTUm3LVRT1SFDisappeared,
tVRTUm3LVRT1SFAlarmReset, tVRTUm3LVRT2L1Activated, tVRTUm3LVRT2L1Disappeared, tVRTUm3LVRT2L1AlarmReset, tVRTUm3LVRT2L2Activated,
tVRTUm3LVRT2L2Disappeared, tVRTUm3LVRT2L2AlarmReset, tVRTUm3LVRT2SFActivated, tVRTUm3LVRT2SFDisappeared, tVRTUm3LVRT2SFAlarmReset,
tVRTUm3LVRT3L1Activated, tVRTUm3LVRT3L1Disappeared, tVRTUm3LVRT3L1AlarmReset, tVRTUm3LVRT3L2Activated, tVRTUm3LVRT3L2Disappeared,
tVRTUm3LVRT3L2AlarmReset, tVRTUm3LVRT3SFActivated, tVRTUm3LVRT3SFDisappeared, tVRTUm3LVRT3SFAlarmReset, tVRTUm12OVRTL1Activated,
tVRTUm12OVRTL1Disappeared, tVRTUm12OVRTL1AlarmReset, tVRTUm12OVRTL2Activated, tVRTUm12OVRTL2Disappeared, tVRTUm12OVRTL2AlarmReset,
tVRTUm12OVRTSFActivated, tVRTUm12OVRTSFDisappeared, tVRTUm12OVRTSFAlarmReset, tVRTUm12LVRT1L1Activated, tVRTUm12LVRT1L1Disappeared,
tVRTUm12LVRT1L1AlarmReset, tVRTUm12LVRT1L2Activated, tVRTUm12LVRT1L2Disappeared, tVRTUm12LVRT1L2AlarmReset, tVRTUm12LVRT1SFActivated,
tVRTUm12LVRT1SFDisappeared, tVRTUm12LVRT1SFAlarmReset, tVRTUm12LVRT2L1Activated, tVRTUm12LVRT2L1Disappeared, tVRTUm12LVRT2L1AlarmReset,
tVRTUm12LVRT2L2Activated, tVRTUm12LVRT2L2Disappeared, tVRTUm12LVRT2L2AlarmReset, tVRTUm12LVRT2SFActivated, tVRTUm12LVRT2SFDisappeared,
tVRTUm12LVRT2SFAlarmReset, tVRTUm12LVRT3L1Activated, tVRTUm12LVRT3L1Disappeared, tVRTUm12LVRT3L1AlarmReset, tVRTUm12LVRT3L2Activated,
tVRTUm12LVRT3L2Disappeared, tVRTUm12LVRT3L2AlarmReset, tVRTUm12LVRT3SFActivated, tVRTUm12LVRT3SFDisappeared, tVRTUm12LVRT3SFAlarmReset,
tVRTUm23OVRTL1Activated, tVRTUm23OVRTL1Disappeared, tVRTUm23OVRTL1AlarmReset, tVRTUm23OVRTL2Activated, tVRTUm23OVRTL2Disappeared,
tVRTUm23OVRTL2AlarmReset, tVRTUm23OVRTSFActivated, tVRTUm23OVRTSFDisappeared, tVRTUm23OVRTSFAlarmReset, tVRTUm23LVRT1L1Activated,
tVRTUm23LVRT1L1Disappeared, tVRTUm23LVRT1L1AlarmReset, tVRTUm23LVRT1L2Activated, tVRTUm23LVRT1L2Disappeared, tVRTUm23LVRT1L2AlarmReset,
tVRTUm23LVRT1SFActivated, tVRTUm23LVRT1SFDisappeared, tVRTUm23LVRT1SFAlarmReset, tVRTUm23LVRT2L1Activated, tVRTUm23LVRT2L1Disappeared,
tVRTUm23LVRT2L1AlarmReset, tVRTUm23LVRT2L2Activated, tVRTUm23LVRT2L2Disappeared, tVRTUm23LVRT2L2AlarmReset, tVRTUm23LVRT2SFActivated,
tVRTUm23LVRT2SFDisappeared, tVRTUm23LVRT2SFAlarmReset, tVRTUm23LVRT3L1Activated, tVRTUm23LVRT3L1Disappeared, tVRTUm23LVRT3L1AlarmReset,
tVRTUm23LVRT3L2Activated, tVRTUm23LVRT3L2Disappeared, tVRTUm23LVRT3L2AlarmReset, tVRTUm23LVRT3SFActivated, tVRTUm23LVRT3SFDisappeared,
tVRTUm23LVRT3SFAlarmReset, tVRTUm31OVRTL1Activated, tVRTUm31OVRTL1Disappeared, tVRTUm31OVRTL1AlarmReset, tVRTUm31OVRTL2Activated,
tVRTUm31OVRTL2Disappeared, tVRTUm31OVRTL2AlarmReset, tVRTUm31OVRTSFActivated, tVRTUm31OVRTSFDisappeared, tVRTUm31OVRTSFAlarmReset,
tVRTUm31LVRT1L1Activated, tVRTUm31LVRT1L1Disappeared, tVRTUm31LVRT1L1AlarmReset, tVRTUm31LVRT1L2Activated, tVRTUm31LVRT1L2Disappeared,
tVRTUm31LVRT1L2AlarmReset, tVRTUm31LVRT1SFActivated, tVRTUm31LVRT1SFDisappeared, tVRTUm31LVRT1SFAlarmReset, tVRTUm31LVRT2L1Activated,
tVRTUm31LVRT2L1Disappeared, tVRTUm31LVRT2L1AlarmReset, tVRTUm31LVRT2L2Activated, tVRTUm31LVRT2L2Disappeared, tVRTUm31LVRT2L2AlarmReset,
tVRTUm31LVRT2SFActivated, tVRTUm31LVRT2SFDisappeared, tVRTUm31LVRT2SFAlarmReset, tVRTUm31LVRT3L1Activated, tVRTUm31LVRT3L1Disappeared,
tVRTUm31LVRT3L1AlarmReset, tVRTUm31LVRT3L2Activated, tVRTUm31LVRT3L2Disappeared, tVRTUm31LVRT3L2AlarmReset, tVRTUm31LVRT3SFActivated,
tVRTUm31LVRT3SFDisappeared, tVRTUm31LVRT3SFAlarmReset, tLVRTUm1SevereL1Activated, tLVRTUm1SevereL1Disappeared, tLVRTUm1SevereL1AlarmReset,
tLVRTUm1SevereL2Activated, tLVRTUm1SevereL2Disappeared, tLVRTUm1SevereL2AlarmReset, tLVRTUm1SevereSFActivated, tLVRTUm1SevereSFDisappeared,
tLVRTUm1SevereSFAlarmReset, tLVRTUm2SevereL1Activated, tLVRTUm2SevereL1Disappeared, tLVRTUm2SevereL1AlarmReset, tLVRTUm2SevereL2Activated,
tLVRTUm2SevereL2Disappeared, tLVRTUm2SevereL2AlarmReset, tLVRTUm2SevereSFActivated, tLVRTUm2SevereSFDisappeared, tLVRTUm2SevereSFAlarmReset,
tLVRTUm3SevereL1Activated, tLVRTUm3SevereL1Disappeared, tLVRTUm3SevereL1AlarmReset, tLVRTUm3SevereL2Activated, tLVRTUm3SevereL2Disappeared,
tLVRTUm3SevereL2AlarmReset, tLVRTUm3SevereSFActivated, tLVRTUm3SevereSFDisappeared, tLVRTUm3SevereSFAlarmReset, tLVRTUm12SevereL1Activated,
tLVRTUm12SevereL1Disappeared, tLVRTUm12SevereL1AlarmReset, tLVRTUm12SevereL2Activated, tLVRTUm12SevereL2Disappeared, tLVRTUm12SevereL2AlarmReset,
tLVRTUm12SevereSFActivated, tLVRTUm12SevereSFDisappeared, tLVRTUm12SevereSFAlarmReset, tLVRTUm23SevereL1Activated, tLVRTUm23SevereL1Disappeared,
tLVRTUm23SevereL1AlarmReset, tLVRTUm23SevereL2Activated, tLVRTUm23SevereL2Disappeared, tLVRTUm23SevereL2AlarmReset, tLVRTUm23SevereSFActivated,
tLVRTUm23SevereSFDisappeared, tLVRTUm23SevereSFAlarmReset, tLVRTUm31SevereL1Activated, tLVRTUm31SevereL1Disappeared, tLVRTUm31SevereL1AlarmReset,
tLVRTUm31SevereL2Activated, tLVRTUm31SevereL2Disappeared, tLVRTUm31SevereL2AlarmReset, tLVRTUm31SevereSFActivated, tLVRTUm31SevereSFDisappeared,
tLVRTUm31SevereSFAlarmReset, tVectorShiftL1Activated, tVectorShiftL1Disappeared, tVectorShiftL1AlarmReset, tROCOF1L1Activated,
tROCOF1L1Disappeared, tROCOF1L1AlarmReset, tROCOF2L1Activated, tROCOF2L1Disappeared, tROCOF2L1AlarmReset,
tROCOF3L1Activated, tROCOF3L1Disappeared, tROCOF3L1AlarmReset, tROCOF4L1Activated, tROCOF4L1Disappeared,
tROCOF4L1AlarmReset, tBatteryVoltsL1Activated, tBatteryVoltsL1Disappeared, tBatteryVoltsL1AlarmReset, tBatteryVoltsL2Activated,
tBatteryVoltsL2Disappeared, tBatteryVoltsL2AlarmReset, tBatteryVoltsSFActivated, tBatteryVoltsSFDisappeared, tBatteryVoltsSFAlarmReset,
tSoftTransferFailL1Activated, tSoftTransferFailL1Disappeared, tSoftTransferFailL1AlarmReset, tRentalTimerBlockStartL1Activated, tRentalTimerBlockStartL1Disappeared,
tRentalTimerBlockStartL1AlarmReset, tManualRestoreL1Activated, tManualRestoreL1Disappeared, tManualRestoreL1AlarmReset, tWrongPowerFormatL1Activated,
tWrongPowerFormatL1Disappeared, tWrongPowerFormatL1AlarmReset, tDeadBusGCBBlockedL1Activated, tDeadBusGCBBlockedL1Disappeared, tDeadBusGCBBlockedL1AlarmReset,
tESTOPL2Activated, tESTOPL2Disappeared, tESTOPL2AlarmReset, tESTOPDash1L2Activated, tESTOPDash1L2Disappeared,
tESTOPDash1L2AlarmReset, tESTOPDash2L2Activated, tESTOPDash2L2Disappeared, tESTOPDash2L2AlarmReset, tESTOPDash3L2Activated,
tESTOPDash3L2Disappeared, tESTOPDash3L2AlarmReset, tESTOPDash4L2Activated, tESTOPDash4L2Disappeared, tESTOPDash4L2AlarmReset,
tESTOPDash5L2Activated, tESTOPDash5L2Disappeared, tESTOPDash5L2AlarmReset, tESTOPDash6L2Activated, tESTOPDash6L2Disappeared,
tESTOPDash6L2AlarmReset, tESTOPDash7L2Activated, tESTOPDash7L2Disappeared, tESTOPDash7L2AlarmReset, tSyncNotAllowedL1Activated,
tSyncNotAllowedL1Disappeared, tSyncNotAllowedL1AlarmReset, tPaveL1Activated, tPaveL1Disappeared, tPaveL1AlarmReset,
tBESSAntiIslandingL1Activated, tBESSAntiIslandingL1Disappeared, tBESSAntiIslandingL1AlarmReset, tMaxNumCUOnCANExceededL2Activated, tMaxNumCUOnCANExceededL2Disappeared,
tMaxNumCUOnCANExceededL2AlarmReset, tCANModule1L1Activated, tCANModule1L1Disappeared, tCANModule1L1AlarmReset, tCANModule1L2Activated,
tCANModule1L2Disappeared, tCANModule1L2AlarmReset, tModuleCHR3ASlot2L1Activated, tModuleCHR3ASlot2L1Disappeared, tModuleCHR3ASlot2L1AlarmReset,
tModuleCHR3ASlot2L2Activated, tModuleCHR3ASlot2L2Disappeared, tModuleCHR3ASlot2L2AlarmReset, tModuleCHR3ASlot3L1Activated, tModuleCHR3ASlot3L1Disappeared,
tModuleCHR3ASlot3L1AlarmReset, tModuleCHR3ASlot3L2Activated, tModuleCHR3ASlot3L2Disappeared, tModuleCHR3ASlot3L2AlarmReset, tModuleCHR3ASlot4L1Activated,
tModuleCHR3ASlot4L1Disappeared, tModuleCHR3ASlot4L1AlarmReset, tModuleCHR3ASlot4L2Activated, tModuleCHR3ASlot4L2Disappeared, tModuleCHR3ASlot4L2AlarmReset,
tModuleCHR3ASlot5L1Activated, tModuleCHR3ASlot5L1Disappeared, tModuleCHR3ASlot5L1AlarmReset, tModuleCHR3ASlot5L2Activated, tModuleCHR3ASlot5L2Disappeared,
tModuleCHR3ASlot5L2AlarmReset, tModuleBroSlotABrcFalseModuleL1Activated, tModuleBroSlotABrcFalseModuleL1Disappeared, tModuleBroSlotABrcFalseModuleL1AlarmReset, tModuleBroSlotABrcFalseModuleL2Activated,
tModuleBroSlotABrcFalseModuleL2Disappeared, tModuleBroSlotABrcFalseModuleL2AlarmReset, tModuleBroSlotBBrcFalseModuleL1Activated, tModuleBroSlotBBrcFalseModuleL1Disappeared, tModuleBroSlotBBrcFalseModuleL1AlarmReset,
tModuleBroSlotBBrcFalseModuleL2Activated, tModuleBroSlotBBrcFalseModuleL2Disappeared, tModuleBroSlotBBrcFalseModuleL2AlarmReset, tModuleBroSlotABrcUnknownModuleL1Activated, tModuleBroSlotABrcUnknownModuleL1Disappeared,
tModuleBroSlotABrcUnknownModuleL1AlarmReset, tModuleBroSlotABrcUnknownModuleL2Activated, tModuleBroSlotABrcUnknownModuleL2Disappeared, tModuleBroSlotABrcUnknownModuleL2AlarmReset, tModuleBroSlotBBrcUnknownModuleL1Activated,
tModuleBroSlotBBrcUnknownModuleL1Disappeared, tModuleBroSlotBBrcUnknownModuleL1AlarmReset, tModuleBroSlotBBrcUnknownModuleL2Activated, tModuleBroSlotBBrcUnknownModuleL2Disappeared, tModuleBroSlotBBrcUnknownModuleL2AlarmReset,
tModuleBroSlotABrcUnattendedL1Activated, tModuleBroSlotABrcUnattendedL1Disappeared, tModuleBroSlotABrcUnattendedL1AlarmReset, tModuleBroSlotABrcUnattendedL2Activated, tModuleBroSlotABrcUnattendedL2Disappeared,
tModuleBroSlotABrcUnattendedL2AlarmReset, tModuleBroSlotBBrcUnattendedL1Activated, tModuleBroSlotBBrcUnattendedL1Disappeared, tModuleBroSlotBBrcUnattendedL1AlarmReset, tModuleBroSlotBBrcUnattendedL2Activated,
tModuleBroSlotBBrcUnattendedL2Disappeared, tModuleBroSlotBBrcUnattendedL2AlarmReset, tModuleBroSlotABrcCommCHR2EOutageL1Activated, tModuleBroSlotABrcCommCHR2EOutageL1Disappeared, tModuleBroSlotABrcCommCHR2EOutageL1AlarmReset,
tModuleBroSlotABrcCommCHR2EOutageL2Activated, tModuleBroSlotABrcCommCHR2EOutageL2Disappeared, tModuleBroSlotABrcCommCHR2EOutageL2AlarmReset, tModuleBroSlotBBrcCommCHR2EOutageL1Activated, tModuleBroSlotBBrcCommCHR2EOutageL1Disappeared,
tModuleBroSlotBBrcCommCHR2EOutageL1AlarmReset, tModuleBroSlotBBrcCommCHR2EOutageL2Activated, tModuleBroSlotBBrcCommCHR2EOutageL2Disappeared, tModuleBroSlotBBrcCommCHR2EOutageL2AlarmReset, tModuleBroSlotABrcUnexpectedL1Activated,
tModuleBroSlotABrcUnexpectedL1Disappeared, tModuleBroSlotABrcUnexpectedL1AlarmReset, tModuleBroSlotABrcUnexpectedL2Activated, tModuleBroSlotABrcUnexpectedL2Disappeared, tModuleBroSlotABrcUnexpectedL2AlarmReset,
tModuleBroSlotBBrcUnexpectedL1Activated, tModuleBroSlotBBrcUnexpectedL1Disappeared, tModuleBroSlotBBrcUnexpectedL1AlarmReset, tModuleBroSlotBBrcUnexpectedL2Activated, tModuleBroSlotBBrcUnexpectedL2Disappeared,
tModuleBroSlotBBrcUnexpectedL2AlarmReset, tEMBroABrcAMessageLostL1Activated, tEMBroABrcAMessageLostL1Disappeared, tEMBroABrcAMessageLostL1AlarmReset, tEMBroABrcAMessageLostL2Activated,
tEMBroABrcAMessageLostL2Disappeared, tEMBroABrcAMessageLostL2AlarmReset, tEMBroBBrcAMessageLostL1Activated, tEMBroBBrcAMessageLostL1Disappeared, tEMBroBBrcAMessageLostL1AlarmReset,
tEMBroBBrcAMessageLostL2Activated, tEMBroBBrcAMessageLostL2Disappeared, tEMBroBBrcAMessageLostL2AlarmReset, tEMBroABrcConfigurationMistakeL1Activated, tEMBroABrcConfigurationMistakeL1Disappeared,
tEMBroABrcConfigurationMistakeL1AlarmReset, tEMBroABrcConfigurationMistakeL2Activated, tEMBroABrcConfigurationMistakeL2Disappeared, tEMBroABrcConfigurationMistakeL2AlarmReset, tEMBroBBrcConfigurationMistakeL1Activated,
tEMBroBBrcConfigurationMistakeL1Disappeared, tEMBroBBrcConfigurationMistakeL1AlarmReset, tEMBroBBrcConfigurationMistakeL2Activated, tEMBroBBrcConfigurationMistakeL2Disappeared, tEMBroBBrcConfigurationMistakeL2AlarmReset,
tEMBroABrcInsufficientL1Activated, tEMBroABrcInsufficientL1Disappeared, tEMBroABrcInsufficientL1AlarmReset, tEMBroABrcInsufficientL2Activated, tEMBroABrcInsufficientL2Disappeared,
tEMBroABrcInsufficientL2AlarmReset, tEMBroBBrcInsufficientL1Activated, tEMBroBBrcInsufficientL1Disappeared, tEMBroBBrcInsufficientL1AlarmReset, tEMBroBBrcInsufficientL2Activated,
tEMBroBBrcInsufficientL2Disappeared, tEMBroBBrcInsufficientL2AlarmReset, tEMBroABrcMissingOrDamagedL1Activated, tEMBroABrcMissingOrDamagedL1Disappeared, tEMBroABrcMissingOrDamagedL1AlarmReset,
tEMBroABrcMissingOrDamagedL2Activated, tEMBroABrcMissingOrDamagedL2Disappeared, tEMBroABrcMissingOrDamagedL2AlarmReset, tEMBroBBrcMissingOrDamagedL1Activated, tEMBroBBrcMissingOrDamagedL1Disappeared,
tEMBroBBrcMissingOrDamagedL1AlarmReset, tEMBroBBrcMissingOrDamagedL2Activated, tEMBroBBrcMissingOrDamagedL2Disappeared, tEMBroBBrcMissingOrDamagedL2AlarmReset, tEventEMail1FailL1Activated,
tEventEMail1FailL1Disappeared, tEventEMail1FailL1AlarmReset, tEventEMail2FailL1Activated, tEventEMail2FailL1Disappeared, tEventEMail2FailL1AlarmReset,
tEventEMail3FailL1Activated, tEventEMail3FailL1Disappeared, tEventEMail3FailL1AlarmReset, tEventEMail4FailL1Activated, tEventEMail4FailL1Disappeared,
tEventEMail4FailL1AlarmReset, tEventSMS1FailL1Activated, tEventSMS1FailL1Disappeared, tEventSMS1FailL1AlarmReset, tEventSMS2FailL1Activated,
tEventSMS2FailL1Disappeared, tEventSMS2FailL1AlarmReset, tEventSMS3FailL1Activated, tEventSMS3FailL1Disappeared, tEventSMS3FailL1AlarmReset,
tEventSMS4FailL1Activated, tEventSMS4FailL1Disappeared, tEventSMS4FailL1AlarmReset, tAlarmEMail1FailL1Activated, tAlarmEMail1FailL1Disappeared,
tAlarmEMail1FailL1AlarmReset, tAlarmEMail2FailL1Activated, tAlarmEMail2FailL1Disappeared, tAlarmEMail2FailL1AlarmReset, tAlarmEMail3FailL1Activated,
tAlarmEMail3FailL1Disappeared, tAlarmEMail3FailL1AlarmReset, tAlarmEMail4FailL1Activated, tAlarmEMail4FailL1Disappeared, tAlarmEMail4FailL1AlarmReset,
tAlarmSMS1FailL1Activated, tAlarmSMS1FailL1Disappeared, tAlarmSMS1FailL1AlarmReset, tAlarmSMS2FailL1Activated, tAlarmSMS2FailL1Disappeared,
tAlarmSMS2FailL1AlarmReset, tAlarmSMS3FailL1Activated, tAlarmSMS3FailL1Disappeared, tAlarmSMS3FailL1AlarmReset, tAlarmSMS4FailL1Activated,
tAlarmSMS4FailL1Disappeared, tAlarmSMS4FailL1AlarmReset, tSNMPTRAP1FailL1Activated, tSNMPTRAP1FailL1Disappeared, tSNMPTRAP1FailL1AlarmReset,
tSNMPTRAP2FailL1Activated, tSNMPTRAP2FailL1Disappeared, tSNMPTRAP2FailL1AlarmReset, tECUDiagBlockedL1Activated, tECUDiagBlockedL1Disappeared,
tECUDiagBlockedL1AlarmReset, tWrongPLCConfigurationL1Activated, tWrongPLCConfigurationL1Disappeared, tWrongPLCConfigurationL1AlarmReset, tRTCBatteryFlatL1Activated,
tRTCBatteryFlatL1Disappeared, tRTCBatteryFlatL1AlarmReset, tPasswEnterBlockL1Activated, tPasswEnterBlockL1Disappeared, tPasswEnterBlockL1AlarmReset,
tControllerRestartRequiredL1Activated, tControllerRestartRequiredL1Disappeared, tControllerRestartRequiredL1AlarmReset, tHuaweiSUN20002CommFailL1Activated, tHuaweiSUN20002CommFailL1Disappeared,
tHuaweiSUN20002CommFailL1AlarmReset, tHuaweiSUN20002CommFailL2Activated, tHuaweiSUN20002CommFailL2Disappeared, tHuaweiSUN20002CommFailL2AlarmReset, tSOLAXX3110KCommFailL1Activated,
tSOLAXX3110KCommFailL1Disappeared, tSOLAXX3110KCommFailL1AlarmReset, tSOLAXX3110KCommFailL2Activated, tSOLAXX3110KCommFailL2Disappeared, tSOLAXX3110KCommFailL2AlarmReset,
tM4MCommFailL1Activated, tM4MCommFailL1Disappeared, tM4MCommFailL1AlarmReset, tM4MCommFailL2Activated, tM4MCommFailL2Disappeared,
tM4MCommFailL2AlarmReset, tSinexcelPWS1CommFailL1Activated, tSinexcelPWS1CommFailL1Disappeared, tSinexcelPWS1CommFailL1AlarmReset, tSinexcelPWS1CommFailL2Activated,
tSinexcelPWS1CommFailL2Disappeared, tSinexcelPWS1CommFailL2AlarmReset, tRBMSCommFailL1Activated, tRBMSCommFailL1Disappeared, tRBMSCommFailL1AlarmReset,
tRBMSCommFailL2Activated, tRBMSCommFailL2Disappeared, tRBMSCommFailL2AlarmReset, tECU6CommFailL1Activated, tECU6CommFailL1Disappeared,
tECU6CommFailL1AlarmReset, tECU6CommFailL2Activated, tECU6CommFailL2Disappeared, tECU6CommFailL2AlarmReset, tECU7CommFailL1Activated,
tECU7CommFailL1Disappeared, tECU7CommFailL1AlarmReset, tECU7CommFailL2Activated, tECU7CommFailL2Disappeared, tECU7CommFailL2AlarmReset,
tECU8CommFailL1Activated, tECU8CommFailL1Disappeared, tECU8CommFailL1AlarmReset, tECU8CommFailL2Activated, tECU8CommFailL2Disappeared,
tECU8CommFailL2AlarmReset, tECU9CommFailL1Activated, tECU9CommFailL1Disappeared, tECU9CommFailL1AlarmReset, tECU9CommFailL2Activated,
tECU9CommFailL2Disappeared, tECU9CommFailL2AlarmReset, tresL1Activated1, tresL1Disappeared1, tresL1AlarmReset1,
tresL2Activated1, tresL2Disappeared1, tresL2AlarmReset1, tresSFActivated1, tresSFDisappeared1,
tresSFAlarmReset1, tresL1Activated2, tresL1Disappeared2, tresL1AlarmReset2, tresL2Activated2,
tresL2Disappeared2, tresL2AlarmReset2, tresSFActivated2, tresSFDisappeared2, tresSFAlarmReset2,
tresL1Activated3, tresL1Disappeared3, tresL1AlarmReset3, tresL2Activated3, tresL2Disappeared3,
tresL2AlarmReset3, tresSFActivated3, tresSFDisappeared3, tresSFAlarmReset3, tresL1Activated4,
tresL1Disappeared4, tresL1AlarmReset4, tresL2Activated4, tresL2Disappeared4, tresL2AlarmReset4,
tresSFActivated4, tresSFDisappeared4, tresSFAlarmReset4, tresL1Activated5, tresL1Disappeared5,
tresL1AlarmReset5, tresL2Activated5, tresL2Disappeared5, tresL2AlarmReset5, tresSFActivated5,
tresSFDisappeared5, tresSFAlarmReset5, tresL1Activated6, tresL1Disappeared6, tresL1AlarmReset6,
tresL2Activated6, tresL2Disappeared6, tresL2AlarmReset6, tresSFActivated6, tresSFDisappeared6,
tresSFAlarmReset6, tresL1Activated7, tresL1Disappeared7, tresL1AlarmReset7, tresL2Activated7,
tresL2Disappeared7, tresL2AlarmReset7, tresSFActivated7, tresSFDisappeared7, tresSFAlarmReset7,
tECUYellowLampL1Activated, tECUYellowLampL1Disappeared, tECUYellowLampL1AlarmReset, tECURedLampL1Activated, tECURedLampL1Disappeared,
tECURedLampL1AlarmReset, tECUWaitToStartL1Activated, tECUWaitToStartL1Disappeared, tECUWaitToStartL1AlarmReset, tATTDPFLampL1Activated,
tATTDPFLampL1Disappeared, tATTDPFLampL1AlarmReset, tATTHESTLampL1Activated, tATTHESTLampL1Disappeared, tATTHESTLampL1AlarmReset,
tATTSCRErrorLampL1Activated, tATTSCRErrorLampL1Disappeared, tATTSCRErrorLampL1AlarmReset, tATTDEFLevelLampL1Activated, tATTDEFLevelLampL1Disappeared,
tATTDEFLevelLampL1AlarmReset, tATTInhibitedLampL1Activated, tATTInhibitedLampL1Disappeared, tATTInhibitedLampL1AlarmReset, tATTInterlockActiveL1Activated,
tATTInterlockActiveL1Disappeared, tATTInterlockActiveL1AlarmReset, tATTForceRegenActiveL1Activated, tATTForceRegenActiveL1Disappeared, tATTForceRegenActiveL1AlarmReset,
tDPFRegenWithProtectionsOffL1Activated, tDPFRegenWithProtectionsOffL1Disappeared, tDPFRegenWithProtectionsOffL1AlarmReset, tATTInhibRegenActiveL1Activated, tATTInhibRegenActiveL1Disappeared,
tATTInhibRegenActiveL1AlarmReset, tLSD500ParamWriteFailL1Activated, tLSD500ParamWriteFailL1Disappeared, tLSD500ParamWriteFailL1AlarmReset, tDisplayFailL1Activated,
tDisplayFailL1Disappeared, tDisplayFailL1AlarmReset, tDefaultPasswordL1Activated, tDefaultPasswordL1Disappeared, tDefaultPasswordL1AlarmReset,
tBruteForceProtectionActiveL1Activated, tBruteForceProtectionActiveL1Disappeared, tBruteForceProtectionActiveL1AlarmReset, tProductionModeL1Activated, tProductionModeL1Disappeared,
tProductionModeL1AlarmReset, tPasswordResetEMailAddrIsNotSetL1Activated, tPasswordResetEMailAddrIsNotSetL1Disappeared, tPasswordResetEMailAddrIsNotSetL1AlarmReset, tSHBINCollisionL1Activated,
tSHBINCollisionL1Disappeared, tSHBINCollisionL1AlarmReset, tSHAINCollisionL1Activated, tSHAINCollisionL1Disappeared, tSHAINCollisionL1AlarmReset,
tSHBIN1L1Activated, tSHBIN1L1Disappeared, tSHBIN1L1AlarmReset, tSHBIN1L2Activated, tSHBIN1L2Disappeared,
tSHBIN1L2AlarmReset, tSHBIN2L1Activated, tSHBIN2L1Disappeared, tSHBIN2L1AlarmReset, tSHBIN2L2Activated,
tSHBIN2L2Disappeared, tSHBIN2L2AlarmReset, tSHBIN3L1Activated, tSHBIN3L1Disappeared, tSHBIN3L1AlarmReset,
tSHBIN3L2Activated, tSHBIN3L2Disappeared, tSHBIN3L2AlarmReset, tSHBIN4L1Activated, tSHBIN4L1Disappeared,
tSHBIN4L1AlarmReset, tSHBIN4L2Activated, tSHBIN4L2Disappeared, tSHBIN4L2AlarmReset, tSHBIN5L1Activated,
tSHBIN5L1Disappeared, tSHBIN5L1AlarmReset, tSHBIN5L2Activated, tSHBIN5L2Disappeared, tSHBIN5L2AlarmReset,
tSHBIN6L1Activated, tSHBIN6L1Disappeared, tSHBIN6L1AlarmReset, tSHBIN6L2Activated, tSHBIN6L2Disappeared,
tSHBIN6L2AlarmReset, tSHAIN1L1Activated, tSHAIN1L1Disappeared, tSHAIN1L1AlarmReset, tSHAIN1L2Activated,
tSHAIN1L2Disappeared, tSHAIN1L2AlarmReset, tSHAIN2L1Activated, tSHAIN2L1Disappeared, tSHAIN2L1AlarmReset,
tSHAIN2L2Activated, tSHAIN2L2Disappeared, tSHAIN2L2AlarmReset, tresL1Activated8, tresL1Disappeared8,
tresL1AlarmReset8, tresL2Activated8, tresL2Disappeared8, tresL2AlarmReset8, tresSFActivated8,
tresSFDisappeared8, tresSFAlarmReset8, tresL1Activated9, tresL1Disappeared9, tresL1AlarmReset9,
tresL2Activated9, tresL2Disappeared9, tresL2AlarmReset9, tresSFActivated9, tresSFDisappeared9,
tresSFAlarmReset9, tStopFailL1Activated, tStopFailL1Disappeared, tStopFailL1AlarmReset, tMaintenanceTimer1RunHoursL1Activated,
tMaintenanceTimer1RunHoursL1Disappeared, tMaintenanceTimer1RunHoursL1AlarmReset, tMaintenanceTimer1RunHoursL2Activated, tMaintenanceTimer1RunHoursL2Disappeared, tMaintenanceTimer1RunHoursL2AlarmReset,
tMaintenanceTimer2RunHoursL1Activated, tMaintenanceTimer2RunHoursL1Disappeared, tMaintenanceTimer2RunHoursL1AlarmReset, tMaintenanceTimer2RunHoursL2Activated, tMaintenanceTimer2RunHoursL2Disappeared,
tMaintenanceTimer2RunHoursL2AlarmReset, tMaintenanceTimer3RunHoursL1Activated, tMaintenanceTimer3RunHoursL1Disappeared, tMaintenanceTimer3RunHoursL1AlarmReset, tMaintenanceTimer3RunHoursL2Activated,
tMaintenanceTimer3RunHoursL2Disappeared, tMaintenanceTimer3RunHoursL2AlarmReset, tMaintenanceTimer4RunHoursL1Activated, tMaintenanceTimer4RunHoursL1Disappeared, tMaintenanceTimer4RunHoursL1AlarmReset,
tMaintenanceTimer4RunHoursL2Activated, tMaintenanceTimer4RunHoursL2Disappeared, tMaintenanceTimer4RunHoursL2AlarmReset, tMaintenanceTimer1IntervalL1Activated, tMaintenanceTimer1IntervalL1Disappeared,
tMaintenanceTimer1IntervalL1AlarmReset, tMaintenanceTimer1IntervalL2Activated, tMaintenanceTimer1IntervalL2Disappeared, tMaintenanceTimer1IntervalL2AlarmReset, tMaintenanceTimer2IntervalL1Activated,
tMaintenanceTimer2IntervalL1Disappeared, tMaintenanceTimer2IntervalL1AlarmReset, tMaintenanceTimer2IntervalL2Activated, tMaintenanceTimer2IntervalL2Disappeared, tMaintenanceTimer2IntervalL2AlarmReset,
tMaintenanceTimer3IntervalL1Activated, tMaintenanceTimer3IntervalL1Disappeared, tMaintenanceTimer3IntervalL1AlarmReset, tMaintenanceTimer3IntervalL2Activated, tMaintenanceTimer3IntervalL2Disappeared,
tMaintenanceTimer3IntervalL2AlarmReset, tMaintenanceTimer4IntervalL1Activated, tMaintenanceTimer4IntervalL1Disappeared, tMaintenanceTimer4IntervalL1AlarmReset, tMaintenanceTimer4IntervalL2Activated,
tMaintenanceTimer4IntervalL2Disappeared, tMaintenanceTimer4IntervalL2AlarmReset, tStartFailL2Activated, tStartFailL2Disappeared, tStartFailL2AlarmReset,
tMCBFailL1Activated, tMCBFailL1Disappeared, tMCBFailL1AlarmReset, tMCBFailToOpenL1Activated, tMCBFailToOpenL1Disappeared,
tMCBFailToOpenL1AlarmReset, tMCBFailToCloseL1Activated, tMCBFailToCloseL1Disappeared, tMCBFailToCloseL1AlarmReset, tBCBFailL2Activated,
tBCBFailL2Disappeared, tBCBFailL2AlarmReset, tBCBFailToOpenL2Activated, tBCBFailToOpenL2Disappeared, tBCBFailToOpenL2AlarmReset,
tBCBFailToCloseL2Activated, tBCBFailToCloseL2Disappeared, tBCBFailToCloseL2AlarmReset, tBCBSecondaryFailL2Activated, tBCBSecondaryFailL2Disappeared,
tBCBSecondaryFailL2AlarmReset, tBCBSecondaryFailToOpenL2Activated, tBCBSecondaryFailToOpenL2Disappeared, tBCBSecondaryFailToOpenL2AlarmReset, tBCBSecondaryFailToCloseL2Activated,
tBCBSecondaryFailToCloseL2Disappeared, tBCBSecondaryFailToCloseL2AlarmReset, tPVCBFailL1Activated, tPVCBFailL1Disappeared, tPVCBFailL1AlarmReset,
tPVCBFailToOpenL1Activated, tPVCBFailToOpenL1Disappeared, tPVCBFailToOpenL1AlarmReset, tPVCBFailToCloseL1Activated, tPVCBFailToCloseL1Disappeared,
tPVCBFailToCloseL1AlarmReset, tBESSGtGtVL1NL2Activated, tBESSGtGtVL1NL2Disappeared, tBESSGtGtVL1NL2AlarmReset, tBESSGtGtVL2NL2Activated,
tBESSGtGtVL2NL2Disappeared, tBESSGtGtVL2NL2AlarmReset, tBESSGtGtVL3NL2Activated, tBESSGtGtVL3NL2Disappeared, tBESSGtGtVL3NL2AlarmReset,
tBESSGtGtVL1L2L2Activated, tBESSGtGtVL1L2L2Disappeared, tBESSGtGtVL1L2L2AlarmReset, tBESSGtGtVL2L3L2Activated, tBESSGtGtVL2L3L2Disappeared,
tBESSGtGtVL2L3L2AlarmReset, tBESSGtGtVL3L1L2Activated, tBESSGtGtVL3L1L2Disappeared, tBESSGtGtVL3L1L2AlarmReset, tBESSGtVL1NL2Activated,
tBESSGtVL1NL2Disappeared, tBESSGtVL1NL2AlarmReset, tBESSGtVL2NL2Activated, tBESSGtVL2NL2Disappeared, tBESSGtVL2NL2AlarmReset,
tBESSGtVL3NL2Activated, tBESSGtVL3NL2Disappeared, tBESSGtVL3NL2AlarmReset, tBESSGtVL1L2L2Activated, tBESSGtVL1L2L2Disappeared,
tBESSGtVL1L2L2AlarmReset, tBESSGtVL2L3L2Activated, tBESSGtVL2L3L2Disappeared, tBESSGtVL2L3L2AlarmReset, tBESSGtVL3L1L2Activated,
tBESSGtVL3L1L2Disappeared, tBESSGtVL3L1L2AlarmReset, tBESSLtVL1NL2Activated, tBESSLtVL1NL2Disappeared, tBESSLtVL1NL2AlarmReset,
tBESSLtVL2NL2Activated, tBESSLtVL2NL2Disappeared, tBESSLtVL2NL2AlarmReset, tBESSLtVL3NL2Activated, tBESSLtVL3NL2Disappeared,
tBESSLtVL3NL2AlarmReset, tBESSLtVL1L2L2Activated, tBESSLtVL1L2L2Disappeared, tBESSLtVL1L2L2AlarmReset, tBESSLtVL2L3L2Activated,
tBESSLtVL2L3L2Disappeared, tBESSLtVL2L3L2AlarmReset, tBESSLtVL3L1L2Activated, tBESSLtVL3L1L2Disappeared, tBESSLtVL3L1L2AlarmReset,
tBESSVUnbalancePhPhL2Activated2, tBESSVUnbalancePhPhL2Disappeared2, tBESSVUnbalancePhPhL2AlarmReset2, tBESSVUnbalancePhNL2Activated2, tBESSVUnbalancePhNL2Disappeared2,
tBESSVUnbalancePhNL2AlarmReset2, tBESSGtFL2Activated, tBESSGtFL2Disappeared, tBESSGtFL2AlarmReset, tBESSLtFL2Activated,
tBESSLtFL2Disappeared, tBESSLtFL2AlarmReset, tBESSCurrentUnbalanceL2Activated2, tBESSCurrentUnbalanceL2Disappeared2, tBESSCurrentUnbalanceL2AlarmReset2,
tQAmpUProtUm12L1Activated, tQAmpUProtUm12L1Disappeared, tQAmpUProtUm12L1AlarmReset, tQAmpUProtUm12L2Activated, tQAmpUProtUm12L2Disappeared,
tQAmpUProtUm12L2AlarmReset, tQAmpUProtUm12SFActivated, tQAmpUProtUm12SFDisappeared, tQAmpUProtUm12SFAlarmReset, tQAmpUProtUm23L1Activated,
tQAmpUProtUm23L1Disappeared, tQAmpUProtUm23L1AlarmReset, tQAmpUProtUm23L2Activated, tQAmpUProtUm23L2Disappeared, tQAmpUProtUm23L2AlarmReset,
tQAmpUProtUm23SFActivated, tQAmpUProtUm23SFDisappeared, tQAmpUProtUm23SFAlarmReset, tQAmpUProtUm31L1Activated, tQAmpUProtUm31L1Disappeared,
tQAmpUProtUm31L1AlarmReset, tQAmpUProtUm31L2Activated, tQAmpUProtUm31L2Disappeared, tQAmpUProtUm31L2AlarmReset, tQAmpUProtUm31SFActivated,
tQAmpUProtUm31SFDisappeared, tQAmpUProtUm31SFAlarmReset, tQAmpUProtQPartL1Activated, tQAmpUProtQPartL1Disappeared, tQAmpUProtQPartL1AlarmReset,
tQAmpUProtQPartL2Activated, tQAmpUProtQPartL2Disappeared, tQAmpUProtQPartL2AlarmReset, tQAmpUProtQPartSFActivated, tQAmpUProtQPartSFDisappeared,
tQAmpUProtQPartSFAlarmReset, tQAmpUProtectionL1Activated, tQAmpUProtectionL1Disappeared, tQAmpUProtectionL1AlarmReset, tVRTProtectionTripL1Activated1,
tVRTProtectionTripL1Disappeared1, tVRTProtectionTripL1AlarmReset1, tVRTProtectionTripL1Activated2, tVRTProtectionTripL1Disappeared2, tVRTProtectionTripL1AlarmReset2,
tVRTProtectionTripL2Activated, tVRTProtectionTripL2Disappeared, tVRTProtectionTripL2AlarmReset, tBESSPhRotationOppositeL1Activated, tBESSPhRotationOppositeL1Disappeared,
tBESSPhRotationOppositeL1AlarmReset, tBESSPhL1InvertedL1Activated, tBESSPhL1InvertedL1Disappeared, tBESSPhL1InvertedL1AlarmReset, tBESSPhL2InvertedL1Activated,
tBESSPhL2InvertedL1Disappeared, tBESSPhL2InvertedL1AlarmReset, tBESSPhL3InvertedL1Activated, tBESSPhL3InvertedL1Disappeared, tBESSPhL3InvertedL1AlarmReset,
tMainsPhRotationOppositeL1Activated, tMainsPhRotationOppositeL1Disappeared, tMainsPhRotationOppositeL1AlarmReset, tMainsPhL1InvertedL1Activated, tMainsPhL1InvertedL1Disappeared,
tMainsPhL1InvertedL1AlarmReset, tMainsPhL2InvertedL1Activated, tMainsPhL2InvertedL1Disappeared, tMainsPhL2InvertedL1AlarmReset, tMainsPhL3InvertedL1Activated,
tMainsPhL3InvertedL1Disappeared, tMainsPhL3InvertedL1AlarmReset, tBusPhRotationOppositeL1Activated, tBusPhRotationOppositeL1Disappeared, tBusPhRotationOppositeL1AlarmReset,
tBusPhL1InvertedL1Activated, tBusPhL1InvertedL1Disappeared, tBusPhL1InvertedL1AlarmReset, tBusPhL2InvertedL1Activated, tBusPhL2InvertedL1Disappeared,
tBusPhL2InvertedL1AlarmReset, tBusPhL3InvertedL1Activated, tBusPhL3InvertedL1Disappeared, tBusPhL3InvertedL1AlarmReset, tOverloadL1Activated,
tOverloadL1Disappeared, tOverloadL1AlarmReset, tIDMTOverloadL2Activated, tIDMTOverloadL2Disappeared, tIDMTOverloadL2AlarmReset,
tShortCircuitL2Activated, tShortCircuitL2Disappeared, tShortCircuitL2AlarmReset, tEarthFaultCurrentL2Activated, tEarthFaultCurrentL2Disappeared,
tEarthFaultCurrentL2AlarmReset, tIDMTBESSGtAL2Activated, tIDMTBESSGtAL2Disappeared, tIDMTBESSGtAL2AlarmReset, tIDMTEarthFaultCurrentL2Activated,
tIDMTEarthFaultCurrentL2Disappeared, tIDMTEarthFaultCurrentL2AlarmReset, tBatteryUndervoltageL1Activated, tBatteryUndervoltageL1Disappeared, tBatteryUndervoltageL1AlarmReset,
tBatteryOvervoltageL1Activated, tBatteryOvervoltageL1Disappeared, tBatteryOvervoltageL1AlarmReset, tOverrideAllSdL1Activated, tOverrideAllSdL1Disappeared,
tOverrideAllSdL1AlarmReset, tReverseSynchroFailL1Activated, tReverseSynchroFailL1Disappeared, tReverseSynchroFailL1AlarmReset, tSynchronizationFailL2Activated,
tSynchronizationFailL2Disappeared, tSynchronizationFailL2AlarmReset, tFrequencyRegulationLimitL1Activated, tFrequencyRegulationLimitL1Disappeared, tFrequencyRegulationLimitL1AlarmReset,
tVoltageRegulationLimitL1Activated, tVoltageRegulationLimitL1Disappeared, tVoltageRegulationLimitL1AlarmReset, tMainsVoltageDetectedL1Activated, tMainsVoltageDetectedL1Disappeared,
tMainsVoltageDetectedL1AlarmReset, tFence1AlarmL1Activated1, tFence1AlarmL1Disappeared1, tFence1AlarmL1AlarmReset1, tFence1AlarmL2Activated1,
tFence1AlarmL2Disappeared1, tFence1AlarmL2AlarmReset1, tFence1AlarmL1Activated2, tFence1AlarmL1Disappeared2, tFence1AlarmL1AlarmReset2,
tFence1AlarmL2Activated2, tFence1AlarmL2Disappeared2, tFence1AlarmL2AlarmReset2, tFence2AlarmL1Activated1, tFence2AlarmL1Disappeared1,
tFence2AlarmL1AlarmReset1, tFence2AlarmL2Activated1, tFence2AlarmL2Disappeared1, tFence2AlarmL2AlarmReset1, tFence2AlarmL1Activated2,
tFence2AlarmL1Disappeared2, tFence2AlarmL1AlarmReset2, tFence2AlarmL2Activated2, tFence2AlarmL2Disappeared2, tFence2AlarmL2AlarmReset2,
tUniversalGensetOverflowL1Activated, tUniversalGensetOverflowL1Disappeared, tUniversalGensetOverflowL1AlarmReset, tBusMeasErrorL2Activated, tBusMeasErrorL2Disappeared,
tBusMeasErrorL2AlarmReset, tNCBFailL2Activated, tNCBFailL2Disappeared, tNCBFailL2AlarmReset, tUnsupportedPMSModeL1Activated,
tUnsupportedPMSModeL1Disappeared, tUnsupportedPMSModeL1AlarmReset, tWrongGCBControlModeL1Activated, tWrongGCBControlModeL1Disappeared, tWrongGCBControlModeL1AlarmReset,
tTotalEmergencyStopL2Activated, tTotalEmergencyStopL2Disappeared, tTotalEmergencyStopL2AlarmReset, tLoadIMPCHR2FEXPFailL1Activated, tLoadIMPCHR2FEXPFailL1Disappeared,
tLoadIMPCHR2FEXPFailL1AlarmReset, tPFCHR2FQIMPCHR2FEXPFailL1Activated, tPFCHR2FQIMPCHR2FEXPFailL1Disappeared, tPFCHR2FQIMPCHR2FEXPFailL1AlarmReset, tPFControlFailL1Activated,
tPFControlFailL1Disappeared, tPFControlFailL1AlarmReset, tQControlFailL1Activated, tQControlFailL1Disappeared, tQControlFailL1AlarmReset,
tQBroUmBrcFailL1Activated, tQBroUmBrcFailL1Disappeared, tQBroUmBrcFailL1AlarmReset, tQrefCHR2FUlimFailL1Activated, tQrefCHR2FUlimFailL1Disappeared,
tQrefCHR2FUlimFailL1AlarmReset, tQBroPBrcFailL1Activated, tQBroPBrcFailL1Disappeared, tQBroPBrcFailL1AlarmReset, tPFBroPmBrcFailL1Activated,
tPFBroPmBrcFailL1Disappeared, tPFBroPmBrcFailL1AlarmReset, tTestUPQFL1Activated, tTestUPQFL1Disappeared, tTestUPQFL1AlarmReset,
tPForQFailL1Activated, tPForQFailL1Disappeared, tPForQFailL1AlarmReset, tPBroUmBrcFailL1Activated, tPBroUmBrcFailL1Disappeared,
tPBroUmBrcFailL1AlarmReset, tStartBlockingL1Activated, tStartBlockingL1Disappeared, tStartBlockingL1AlarmReset, tDailyBatteryCyclesReachedL1Activated,
tDailyBatteryCyclesReachedL1Disappeared, tDailyBatteryCyclesReachedL1AlarmReset, tCANIntercontrollerEmptyL1Activated, tCANIntercontrollerEmptyL1Disappeared, tCANIntercontrollerEmptyL1AlarmReset,
tresL1Activated10, tresL1Disappeared10, tresL1AlarmReset10, tSWKeyModbusMasterErrorL1Activated, tSWKeyModbusMasterErrorL1Disappeared,
tSWKeyModbusMasterErrorL1AlarmReset, tresL1Activated11, tresL1Disappeared11, tresL1AlarmReset11, tresL1Activated12,
tresL1Disappeared12, tresL1AlarmReset12, tresL1Activated13, tresL1Disappeared13, tresL1AlarmReset13,
tresL1Activated14, tresL1Disappeared14, tresL1AlarmReset14, tresL1Activated15, tresL1Disappeared15,
tresL1AlarmReset15, tresL1Activated16, tresL1Disappeared16, tresL1AlarmReset16, tresL1Activated17,
tresL1Disappeared17, tresL1AlarmReset17, tresL1Activated18, tresL1Disappeared18, tresL1AlarmReset18,
tresL1Activated19, tresL1Disappeared19, tresL1AlarmReset19, tSWKeyCANControllersErrorL1Activated, tSWKeyCANControllersErrorL1Disappeared,
tSWKeyCANControllersErrorL1AlarmReset, tresL1Activated20, tresL1Disappeared20, tresL1AlarmReset20, tresL1Activated21,
tresL1Disappeared21, tresL1AlarmReset21, tUniGenSWKeyMissingL1Activated, tUniGenSWKeyMissingL1Disappeared, tUniGenSWKeyMissingL1AlarmReset,
tPVNotOperableL2Activated, tPVNotOperableL2Disappeared, tPVNotOperableL2AlarmReset, tPVAntiIslandingL2Activated, tPVAntiIslandingL2Disappeared,
tPVAntiIslandingL2AlarmReset, tSOCLowAlarmL1Activated, tSOCLowAlarmL1Disappeared, tSOCLowAlarmL1AlarmReset, tSOCHighAlarmL1Activated,
tSOCHighAlarmL1Disappeared, tSOCHighAlarmL1AlarmReset, tSOCCriticalLowL2Activated, tSOCCriticalLowL2Disappeared, tSOCCriticalLowL2AlarmReset,
tSOCCriticalHighL2Activated, tSOCCriticalHighL2Disappeared, tSOCCriticalHighL2AlarmReset, tBESSSOCNotConfiguredL2Activated, tBESSSOCNotConfiguredL2Disappeared,
tBESSSOCNotConfiguredL2AlarmReset, tBESSSOCNotAvailableL2Activated, tBESSSOCNotAvailableL2Disappeared, tBESSSOCNotAvailableL2AlarmReset, tDCCircuitCloseFailL2Activated,
tDCCircuitCloseFailL2Disappeared, tDCCircuitCloseFailL2AlarmReset, tBCBClosingIsBlockedL1Activated, tBCBClosingIsBlockedL1Disappeared, tBCBClosingIsBlockedL1AlarmReset,
tEMBroABrcAMessageLost, tEMBroBBrcAMessageLost, tFaultReset, tEventEMail1OK, tEventEMail2OK,
tEventEMail3OK, tEventEMail4OK, tEventSMS1OK, tEventSMS2OK, tEventSMS3OK,
tEventSMS4OK, tAlarmEMail1OK, tAlarmEMail2OK, tAlarmEMail3OK, tAlarmEMail4OK,
tAlarmSMS1OK, tAlarmSMS2OK, tAlarmSMS3OK, tAlarmSMS4OK, tSNMPTRAP1OK,
tSNMPTRAP2OK, tEventEMail1Fail, tEventEMail2Fail, tEventEMail3Fail, tEventEMail4Fail,
tEventSMS1Fail, tEventSMS2Fail, tEventSMS3Fail, tEventSMS4Fail, tAlarmEMail1Fail,
tAlarmEMail2Fail, tAlarmEMail3Fail, tAlarmEMail4Fail, tAlarmSMS1Fail, tAlarmSMS2Fail,
tAlarmSMS3Fail, tAlarmSMS4Fail, tSNMPTRAP1Fail, tSNMPTRAP2Fail, tSwitchedOn,
tWatchdog, tSystem, tSystemLog, tWrongConfig, tSetpointChange,
tPasswordSet, tPasswordChng, tAccessCodeSet, tAccessCodeChng, tTerminal,
tForcedValue, tTimeModeChange, tGroupsLinked, tGroupsUnlinked, tProgrammingRequest,
tProgrammingNotFinished, tProgrammingResult, tUnknownECUDiag, tTerminalDiag, tTimeStamp,
tLVRTSevere, tMaintenance1, tMaintenance2, tMaintenance3, tVectorShift,
tROCOF, tReverseSynchroFail, tSynchronisationFail, tMainsFail, tMainsReturned,
tLoadOnMains, tLoadOnBESS, tPeakStart, tPMSStart, tModbusRemoteStart,
tRemoteStart, tAMFStart, tManualStart, tTestStart, tOtherStop,
tManualStop, tAMFStop, tRemoteStop, tPeakStop, tPMSStop,
tModbusRemoteStop, tDCBusDeenergized, tBCBOpened, tBCBOpenedExternally, tBCBClosed,
tBCBClosedExternally, tMCBOpened, tMCBOpenedExternally, tMCBClosed, tMCBClosedExternally,
tSyncStarted, tRevSyncStarted, tReady, tEnergized, tSoftLoad,
tLoaded, tSoftUnload, tEmergMAN, tNotReady, tTestOnLoad,
tLoadShed, tLoadReconnect, tFence1Alarm, tFence2Alarm, tOtherCBTrip,
tEmergencyDroopInactive, tProtectionForceDisable1Active, tProtectionForceDisable1Inactive, tProtectionForceDisable2Active, tProtectionForceDisable2Inactive,
tProtectionForceDisable3Active, tProtectionForceDisable3Inactive, tProtectionForceDisable4Active, tProtectionForceDisable4Inactive, tMissingSWKey,
tUserLogin, tUserLogout, tMaintenanceTimer1Reset, tMaintenanceTimer2Reset, tMaintenanceTimer3Reset,
tMaintenanceTimer4Reset, tPVCBOpened, tPVCBClosed }
	STATUS  current
	DESCRIPTION  "Notifications"
	::= { conformanceGroups 6 }

tMCBFeedbackL1Activated	NOTIFICATION-TYPE
	OBJECTS	{tControllerName, tSerNum, tTrapText}
	STATUS	current
	DESCRIPTION	"Protection 1. level - MCB Feedback - alarm activated"
::= { notifications 8388612 }

tMCBFeedbackL1Disappeared	NOTIFICATION-TYPE
	OBJECTS	{tControllerName, tSerNum, tTrapText}
	STATUS	current
	DESCRIPTION	"Protection 1. level - MCB Feedback - alarm disappeared"
::= { notifications 8388613 }

tMCBFeedbackL1AlarmReset	NOTIFICATION-TYPE
	OBJECTS	{tControllerName, tSerNum, tTrapText}
	STATUS	current
	DESCRIPTION	"Protection 1. level - MCB Feedback - alarm reset"
::= { notifications 8388614 }

tMCBFeedbackL2Activated	NOTIFICATION-TYPE
	OBJECTS	{tControllerName, tSerNum, tTrapText}
	STATUS	current
	DESCRIPTION	"Protection 2. level - MCB Feedback - alarm activated"
::= { notifications 142606340 }

tMCBFeedbackL2Disappeared	NOTIFICATION-TYPE
	OBJECTS	{tControllerName, tSerNum, tTrapText}
	STATUS	current
	DESCRIPTION	"Protection 2. level - MCB Feedback - alarm disappeared"
::= { notifications 142606341 }

tMCBFeedbackL2AlarmReset	NOTIFICATION-TYPE
	OBJECTS	{tControllerName, tSerNum, tTrapText}
	STATUS	current
	DESCRIPTION	"Protection 2. level - MCB Feedback - alarm reset"
::= { notifications 142606342 }

tMCBFeedbackSFActivated	NOTIFICATION-TYPE
	OBJECTS	{tControllerName, tSerNum, tTrapText}
	STATUS	current
	DESCRIPTION	"Protection Sensor Fail - MCB Feedback - alarm activated"
::= { notifications 276824068 }

tMCBFeedbackSFDisappeared	NOTIFICATION-TYPE
	OBJECTS	{tControllerName, tSerNum, tTrapText}
	STATUS	current
	DESCRIPTION	"Protection Sensor Fail - MCB Feedback - alarm disappeared"
::= { notifications 276824069 }

tMCBFeedbackSFAlarmReset	NOTIFICATION-TYPE
	OBJECTS	{tControllerName, tSerNum, tTrapText}
	STATUS	current
	DESCRIPTION	"Protection Sensor Fail - MCB Feedback - alarm reset"
::= { notifications 276824070 }

tBESSReadyToLoadL1Activated	NOTIFICATION-TYPE
	OBJECTS	{tControllerName, tSerNum, tTrapText}
	STATUS	current
	DESCRIPTION	"Protection 1. level - BESS Ready To Load - alarm activated"
::= { notifications 8388616 }

tBESSReadyToLoadL1Disappeared	NOTIFICATION-TYPE
	OBJECTS	{tControllerName, tSerNum, tTrapText}
	STATUS	current
	DESCRIPTION	"Protection 1. level - BESS Ready To Load - alarm disappeared"
::= { notifications 8388617 }

tBESSReadyToLoadL1AlarmReset	NOTIFICATION-TYPE
	OBJECTS	{tControllerName, tSerNum, tTrapText}
	STATUS	current
	DESCRIPTION	"Protection 1. level - BESS Ready To Load - alarm reset"
::= { notifications 8388618 }

tBESSReadyToLoadL2Activated	NOTIFICATION-TYPE
	OBJECTS	{tControllerName, tSerNum, tTrapText}
	STATUS	current
	DESCRIPTION	"Protection 2. level - BESS Ready To Load - alarm activated"
::= { notifications 142606344 }

tBESSReadyToLoadL2Disappeared	NOTIFICATION-TYPE
	OBJECTS	{tControllerName, tSerNum, tTrapText}
	STATUS	current
	DESCRIPTION	"Protection 2. level - BESS Ready To Load - alarm disappeared"
::= { notifications 142606345 }

tBESSReadyToLoadL2AlarmReset	NOTIFICATION-TYPE
	OBJECTS	{tControllerName, tSerNum, tTrapText}
	STATUS	current
	DESCRIPTION	"Protection 2. level - BESS Ready To Load - alarm reset"
::= { notifications 142606346 }

tBESSReadyToLoadSFActivated	NOTIFICATION-TYPE
	OBJECTS	{tControllerName, tSerNum, tTrapText}
	STATUS	current
	DESCRIPTION	"Protection Sensor Fail - BESS Ready To Load - alarm activated"
::= { notifications 276824072 }

tBESSReadyToLoadSFDisappeared	NOTIFICATION-TYPE
	OBJECTS	{tControllerName, tSerNum, tTrapText}
	STATUS	current
	DESCRIPTION	"Protection Sensor Fail - BESS Ready To Load - alarm disappeared"
::= { notifications 276824073 }

tBESSReadyToLoadSFAlarmReset	NOTIFICATION-TYPE
	OBJECTS	{tControllerName, tSerNum, tTrapText}
	STATUS	current
	DESCRIPTION	"Protection Sensor Fail - BESS Ready To Load - alarm reset"
::= { notifications 276824074 }

tPVCBFeedbackL1Activated	NOTIFICATION-TYPE
	OBJECTS	{tControllerName, tSerNum, tTrapText}
	STATUS	current
	DESCRIPTION	"Protection 1. level - PVCB Feedback - alarm activated"
::= { notifications 8388620 }

tPVCBFeedbackL1Disappeared	NOTIFICATION-TYPE
	OBJECTS	{tControllerName, tSerNum, tTrapText}
	STATUS	current
	DESCRIPTION	"Protection 1. level - PVCB Feedback - alarm disappeared"
::= { notifications 8388621 }

tPVCBFeedbackL1AlarmReset	NOTIFICATION-TYPE
	OBJECTS	{tControllerName, tSerNum, tTrapText}
	STATUS	current
	DESCRIPTION	"Protection 1. level - PVCB Feedback - alarm reset"
::= { notifications 8388622 }

tPVCBFeedbackL2Activated	NOTIFICATION-TYPE
	OBJECTS	{tControllerName, tSerNum, tTrapText}
	STATUS	current
	DESCRIPTION	"Protection 2. level - PVCB Feedback - alarm activated"
::= { notifications 142606348 }

tPVCBFeedbackL2Disappeared	NOTIFICATION-TYPE
	OBJECTS	{tControllerName, tSerNum, tTrapText}
	STATUS	current
	DESCRIPTION	"Protection 2. level - PVCB Feedback - alarm disappeared"
::= { notifications 142606349 }

tPVCBFeedbackL2AlarmReset	NOTIFICATION-TYPE
	OBJECTS	{tControllerName, tSerNum, tTrapText}
	STATUS	current
	DESCRIPTION	"Protection 2. level - PVCB Feedback - alarm reset"
::= { notifications 142606350 }

tPVCBFeedbackSFActivated	NOTIFICATION-TYPE
	OBJECTS	{tControllerName, tSerNum, tTrapText}
	STATUS	current
	DESCRIPTION	"Protection Sensor Fail - PVCB Feedback - alarm activated"
::= { notifications 276824076 }

tPVCBFeedbackSFDisappeared	NOTIFICATION-TYPE
	OBJECTS	{tControllerName, tSerNum, tTrapText}
	STATUS	current
	DESCRIPTION	"Protection Sensor Fail - PVCB Feedback - alarm disappeared"
::= { notifications 276824077 }

tPVCBFeedbackSFAlarmReset	NOTIFICATION-TYPE
	OBJECTS	{tControllerName, tSerNum, tTrapText}
	STATUS	current
	DESCRIPTION	"Protection Sensor Fail - PVCB Feedback - alarm reset"
::= { notifications 276824078 }

tRemoteOFFL1Activated	NOTIFICATION-TYPE
	OBJECTS	{tControllerName, tSerNum, tTrapText}
	STATUS	current
	DESCRIPTION	"Protection 1. level - Remote OFF - alarm activated"
::= { notifications 8388624 }

tRemoteOFFL1Disappeared	NOTIFICATION-TYPE
	OBJECTS	{tControllerName, tSerNum, tTrapText}
	STATUS	current
	DESCRIPTION	"Protection 1. level - Remote OFF - alarm disappeared"
::= { notifications 8388625 }

tRemoteOFFL1AlarmReset	NOTIFICATION-TYPE
	OBJECTS	{tControllerName, tSerNum, tTrapText}
	STATUS	current
	DESCRIPTION	"Protection 1. level - Remote OFF - alarm reset"
::= { notifications 8388626 }

tRemoteOFFL2Activated	NOTIFICATION-TYPE
	OBJECTS	{tControllerName, tSerNum, tTrapText}
	STATUS	current
	DESCRIPTION	"Protection 2. level - Remote OFF - alarm activated"
::= { notifications 142606352 }

tRemoteOFFL2Disappeared	NOTIFICATION-TYPE
	OBJECTS	{tControllerName, tSerNum, tTrapText}
	STATUS	current
	DESCRIPTION	"Protection 2. level - Remote OFF - alarm disappeared"
::= { notifications 142606353 }

tRemoteOFFL2AlarmReset	NOTIFICATION-TYPE
	OBJECTS	{tControllerName, tSerNum, tTrapText}
	STATUS	current
	DESCRIPTION	"Protection 2. level - Remote OFF - alarm reset"
::= { notifications 142606354 }

tRemoteOFFSFActivated	NOTIFICATION-TYPE
	OBJECTS	{tControllerName, tSerNum, tTrapText}
	STATUS	current
	DESCRIPTION	"Protection Sensor Fail - Remote OFF - alarm activated"
::= { notifications 276824080 }

tRemoteOFFSFDisappeared	NOTIFICATION-TYPE
	OBJECTS	{tControllerName, tSerNum, tTrapText}
	STATUS	current
	DESCRIPTION	"Protection Sensor Fail - Remote OFF - alarm disappeared"
::= { notifications 276824081 }

tRemoteOFFSFAlarmReset	NOTIFICATION-TYPE
	OBJECTS	{tControllerName, tSerNum, tTrapText}
	STATUS	current
	DESCRIPTION	"Protection Sensor Fail - Remote OFF - alarm reset"
::= { notifications 276824082 }

tPrechargeFinishedL1Activated	NOTIFICATION-TYPE
	OBJECTS	{tControllerName, tSerNum, tTrapText}
	STATUS	current
	DESCRIPTION	"Protection 1. level - Precharge Finished - alarm activated"
::= { notifications 8388628 }

tPrechargeFinishedL1Disappeared	NOTIFICATION-TYPE
	OBJECTS	{tControllerName, tSerNum, tTrapText}
	STATUS	current
	DESCRIPTION	"Protection 1. level - Precharge Finished - alarm disappeared"
::= { notifications 8388629 }

tPrechargeFinishedL1AlarmReset	NOTIFICATION-TYPE
	OBJECTS	{tControllerName, tSerNum, tTrapText}
	STATUS	current
	DESCRIPTION	"Protection 1. level - Precharge Finished - alarm reset"
::= { notifications 8388630 }

tPrechargeFinishedL2Activated	NOTIFICATION-TYPE
	OBJECTS	{tControllerName, tSerNum, tTrapText}
	STATUS	current
	DESCRIPTION	"Protection 2. level - Precharge Finished - alarm activated"
::= { notifications 142606356 }

tPrechargeFinishedL2Disappeared	NOTIFICATION-TYPE
	OBJECTS	{tControllerName, tSerNum, tTrapText}
	STATUS	current
	DESCRIPTION	"Protection 2. level - Precharge Finished - alarm disappeared"
::= { notifications 142606357 }

tPrechargeFinishedL2AlarmReset	NOTIFICATION-TYPE
	OBJECTS	{tControllerName, tSerNum, tTrapText}
	STATUS	current
	DESCRIPTION	"Protection 2. level - Precharge Finished - alarm reset"
::= { notifications 142606358 }

tPrechargeFinishedSFActivated	NOTIFICATION-TYPE
	OBJECTS	{tControllerName, tSerNum, tTrapText}
	STATUS	current
	DESCRIPTION	"Protection Sensor Fail - Precharge Finished - alarm activated"
::= { notifications 276824084 }

tPrechargeFinishedSFDisappeared	NOTIFICATION-TYPE
	OBJECTS	{tControllerName, tSerNum, tTrapText}
	STATUS	current
	DESCRIPTION	"Protection Sensor Fail - Precharge Finished - alarm disappeared"
::= { notifications 276824085 }

tPrechargeFinishedSFAlarmReset	NOTIFICATION-TYPE
	OBJECTS	{tControllerName, tSerNum, tTrapText}
	STATUS	current
	DESCRIPTION	"Protection Sensor Fail - Precharge Finished - alarm reset"
::= { notifications 276824086 }

tSdOverrideL1Activated	NOTIFICATION-TYPE
	OBJECTS	{tControllerName, tSerNum, tTrapText}
	STATUS	current
	DESCRIPTION	"Protection 1. level - Sd Override - alarm activated"
::= { notifications 8388632 }

tSdOverrideL1Disappeared	NOTIFICATION-TYPE
	OBJECTS	{tControllerName, tSerNum, tTrapText}
	STATUS	current
	DESCRIPTION	"Protection 1. level - Sd Override - alarm disappeared"
::= { notifications 8388633 }

tSdOverrideL1AlarmReset	NOTIFICATION-TYPE
	OBJECTS	{tControllerName, tSerNum, tTrapText}
	STATUS	current
	DESCRIPTION	"Protection 1. level - Sd Override - alarm reset"
::= { notifications 8388634 }

tSdOverrideL2Activated	NOTIFICATION-TYPE
	OBJECTS	{tControllerName, tSerNum, tTrapText}
	STATUS	current
	DESCRIPTION	"Protection 2. level - Sd Override - alarm activated"
::= { notifications 142606360 }

tSdOverrideL2Disappeared	NOTIFICATION-TYPE
	OBJECTS	{tControllerName, tSerNum, tTrapText}
	STATUS	current
	DESCRIPTION	"Protection 2. level - Sd Override - alarm disappeared"
::= { notifications 142606361 }

tSdOverrideL2AlarmReset	NOTIFICATION-TYPE
	OBJECTS	{tControllerName, tSerNum, tTrapText}
	STATUS	current
	DESCRIPTION	"Protection 2. level - Sd Override - alarm reset"
::= { notifications 142606362 }

tSdOverrideSFActivated	NOTIFICATION-TYPE
	OBJECTS	{tControllerName, tSerNum, tTrapText}
	STATUS	current
	DESCRIPTION	"Protection Sensor Fail - Sd Override - alarm activated"
::= { notifications 276824088 }

tSdOverrideSFDisappeared	NOTIFICATION-TYPE
	OBJECTS	{tControllerName, tSerNum, tTrapText}
	STATUS	current
	DESCRIPTION	"Protection Sensor Fail - Sd Override - alarm disappeared"
::= { notifications 276824089 }

tSdOverrideSFAlarmReset	NOTIFICATION-TYPE
	OBJECTS	{tControllerName, tSerNum, tTrapText}
	STATUS	current
	DESCRIPTION	"Protection Sensor Fail - Sd Override - alarm reset"
::= { notifications 276824090 }

tVSGModeOnL1Activated	NOTIFICATION-TYPE
	OBJECTS	{tControllerName, tSerNum, tTrapText}
	STATUS	current
	DESCRIPTION	"Protection 1. level - VSGModeOn - alarm activated"
::= { notifications 8389092 }

tVSGModeOnL1Disappeared	NOTIFICATION-TYPE
	OBJECTS	{tControllerName, tSerNum, tTrapText}
	STATUS	current
	DESCRIPTION	"Protection 1. level - VSGModeOn - alarm disappeared"
::= { notifications 8389093 }

tVSGModeOnL1AlarmReset	NOTIFICATION-TYPE
	OBJECTS	{tControllerName, tSerNum, tTrapText}
	STATUS	current
	DESCRIPTION	"Protection 1. level - VSGModeOn - alarm reset"
::= { notifications 8389094 }

tVSGModeOnL2Activated	NOTIFICATION-TYPE
	OBJECTS	{tControllerName, tSerNum, tTrapText}
	STATUS	current
	DESCRIPTION	"Protection 2. level - VSGModeOn - alarm activated"
::= { notifications 142606820 }

tVSGModeOnL2Disappeared	NOTIFICATION-TYPE
	OBJECTS	{tControllerName, tSerNum, tTrapText}
	STATUS	current
	DESCRIPTION	"Protection 2. level - VSGModeOn - alarm disappeared"
::= { notifications 142606821 }

tVSGModeOnL2AlarmReset	NOTIFICATION-TYPE
	OBJECTS	{tControllerName, tSerNum, tTrapText}
	STATUS	current
	DESCRIPTION	"Protection 2. level - VSGModeOn - alarm reset"
::= { notifications 142606822 }

tVSGModeOnSFActivated	NOTIFICATION-TYPE
	OBJECTS	{tControllerName, tSerNum, tTrapText}
	STATUS	current
	DESCRIPTION	"Protection Sensor Fail - VSGModeOn - alarm activated"
::= { notifications 276824548 }

tVSGModeOnSFDisappeared	NOTIFICATION-TYPE
	OBJECTS	{tControllerName, tSerNum, tTrapText}
	STATUS	current
	DESCRIPTION	"Protection Sensor Fail - VSGModeOn - alarm disappeared"
::= { notifications 276824549 }

tVSGModeOnSFAlarmReset	NOTIFICATION-TYPE
	OBJECTS	{tControllerName, tSerNum, tTrapText}
	STATUS	current
	DESCRIPTION	"Protection Sensor Fail - VSGModeOn - alarm reset"
::= { notifications 276824550 }

tOnOffStatusesL1Activated	NOTIFICATION-TYPE
	OBJECTS	{tControllerName, tSerNum, tTrapText}
	STATUS	current
	DESCRIPTION	"Protection 1. level - OnOffStatuses - alarm activated"
::= { notifications 8389096 }

tOnOffStatusesL1Disappeared	NOTIFICATION-TYPE
	OBJECTS	{tControllerName, tSerNum, tTrapText}
	STATUS	current
	DESCRIPTION	"Protection 1. level - OnOffStatuses - alarm disappeared"
::= { notifications 8389097 }

tOnOffStatusesL1AlarmReset	NOTIFICATION-TYPE
	OBJECTS	{tControllerName, tSerNum, tTrapText}
	STATUS	current
	DESCRIPTION	"Protection 1. level - OnOffStatuses - alarm reset"
::= { notifications 8389098 }

tOnOffStatusesL2Activated	NOTIFICATION-TYPE
	OBJECTS	{tControllerName, tSerNum, tTrapText}
	STATUS	current
	DESCRIPTION	"Protection 2. level - OnOffStatuses - alarm activated"
::= { notifications 142606824 }

tOnOffStatusesL2Disappeared	NOTIFICATION-TYPE
	OBJECTS	{tControllerName, tSerNum, tTrapText}
	STATUS	current
	DESCRIPTION	"Protection 2. level - OnOffStatuses - alarm disappeared"
::= { notifications 142606825 }

tOnOffStatusesL2AlarmReset	NOTIFICATION-TYPE
	OBJECTS	{tControllerName, tSerNum, tTrapText}
	STATUS	current
	DESCRIPTION	"Protection 2. level - OnOffStatuses - alarm reset"
::= { notifications 142606826 }

tOnOffStatusesSFActivated	NOTIFICATION-TYPE
	OBJECTS	{tControllerName, tSerNum, tTrapText}
	STATUS	current
	DESCRIPTION	"Protection Sensor Fail - OnOffStatuses - alarm activated"
::= { notifications 276824552 }

tOnOffStatusesSFDisappeared	NOTIFICATION-TYPE
	OBJECTS	{tControllerName, tSerNum, tTrapText}
	STATUS	current
	DESCRIPTION	"Protection Sensor Fail - OnOffStatuses - alarm disappeared"
::= { notifications 276824553 }

tOnOffStatusesSFAlarmReset	NOTIFICATION-TYPE
	OBJECTS	{tControllerName, tSerNum, tTrapText}
	STATUS	current
	DESCRIPTION	"Protection Sensor Fail - OnOffStatuses - alarm reset"
::= { notifications 276824554 }

tFaultStatusL1Activated	NOTIFICATION-TYPE
	OBJECTS	{tControllerName, tSerNum, tTrapText}
	STATUS	current
	DESCRIPTION	"Protection 1. level - Fault status - alarm activated"
::= { notifications 8389104 }

tFaultStatusL1Disappeared	NOTIFICATION-TYPE
	OBJECTS	{tControllerName, tSerNum, tTrapText}
	STATUS	current
	DESCRIPTION	"Protection 1. level - Fault status - alarm disappeared"
::= { notifications 8389105 }

tFaultStatusL1AlarmReset	NOTIFICATION-TYPE
	OBJECTS	{tControllerName, tSerNum, tTrapText}
	STATUS	current
	DESCRIPTION	"Protection 1. level - Fault status - alarm reset"
::= { notifications 8389106 }

tFaultStatusL2Activated	NOTIFICATION-TYPE
	OBJECTS	{tControllerName, tSerNum, tTrapText}
	STATUS	current
	DESCRIPTION	"Protection 2. level - Fault status - alarm activated"
::= { notifications 142606832 }

tFaultStatusL2Disappeared	NOTIFICATION-TYPE
	OBJECTS	{tControllerName, tSerNum, tTrapText}
	STATUS	current
	DESCRIPTION	"Protection 2. level - Fault status - alarm disappeared"
::= { notifications 142606833 }

tFaultStatusL2AlarmReset	NOTIFICATION-TYPE
	OBJECTS	{tControllerName, tSerNum, tTrapText}
	STATUS	current
	DESCRIPTION	"Protection 2. level - Fault status - alarm reset"
::= { notifications 142606834 }

tFaultStatusSFActivated	NOTIFICATION-TYPE
	OBJECTS	{tControllerName, tSerNum, tTrapText}
	STATUS	current
	DESCRIPTION	"Protection Sensor Fail - Fault status - alarm activated"
::= { notifications 276824560 }

tFaultStatusSFDisappeared	NOTIFICATION-TYPE
	OBJECTS	{tControllerName, tSerNum, tTrapText}
	STATUS	current
	DESCRIPTION	"Protection Sensor Fail - Fault status - alarm disappeared"
::= { notifications 276824561 }

tFaultStatusSFAlarmReset	NOTIFICATION-TYPE
	OBJECTS	{tControllerName, tSerNum, tTrapText}
	STATUS	current
	DESCRIPTION	"Protection Sensor Fail - Fault status - alarm reset"
::= { notifications 276824562 }

tCUAIN01L1Activated	NOTIFICATION-TYPE
	OBJECTS	{tControllerName, tSerNum, tTrapText}
	STATUS	current
	DESCRIPTION	"Protection 1. level - CU-AIN-01 - alarm activated"
::= { notifications 16779008 }

tCUAIN01L1Disappeared	NOTIFICATION-TYPE
	OBJECTS	{tControllerName, tSerNum, tTrapText}
	STATUS	current
	DESCRIPTION	"Protection 1. level - CU-AIN-01 - alarm disappeared"
::= { notifications 16779009 }

tCUAIN01L1AlarmReset	NOTIFICATION-TYPE
	OBJECTS	{tControllerName, tSerNum, tTrapText}
	STATUS	current
	DESCRIPTION	"Protection 1. level - CU-AIN-01 - alarm reset"
::= { notifications 16779010 }

tCUAIN01L2Activated	NOTIFICATION-TYPE
	OBJECTS	{tControllerName, tSerNum, tTrapText}
	STATUS	current
	DESCRIPTION	"Protection 2. level - CU-AIN-01 - alarm activated"
::= { notifications 150996736 }

tCUAIN01L2Disappeared	NOTIFICATION-TYPE
	OBJECTS	{tControllerName, tSerNum, tTrapText}
	STATUS	current
	DESCRIPTION	"Protection 2. level - CU-AIN-01 - alarm disappeared"
::= { notifications 150996737 }

tCUAIN01L2AlarmReset	NOTIFICATION-TYPE
	OBJECTS	{tControllerName, tSerNum, tTrapText}
	STATUS	current
	DESCRIPTION	"Protection 2. level - CU-AIN-01 - alarm reset"
::= { notifications 150996738 }

tCUAIN01SFActivated	NOTIFICATION-TYPE
	OBJECTS	{tControllerName, tSerNum, tTrapText}
	STATUS	current
	DESCRIPTION	"Protection Sensor Fail - CU-AIN-01 - alarm activated"
::= { notifications 285214464 }

tCUAIN01SFDisappeared	NOTIFICATION-TYPE
	OBJECTS	{tControllerName, tSerNum, tTrapText}
	STATUS	current
	DESCRIPTION	"Protection Sensor Fail - CU-AIN-01 - alarm disappeared"
::= { notifications 285214465 }

tCUAIN01SFAlarmReset	NOTIFICATION-TYPE
	OBJECTS	{tControllerName, tSerNum, tTrapText}
	STATUS	current
	DESCRIPTION	"Protection Sensor Fail - CU-AIN-01 - alarm reset"
::= { notifications 285214466 }

tActivePowerL1Activated1	NOTIFICATION-TYPE
	OBJECTS	{tControllerName, tSerNum, tTrapText}
	STATUS	current
	DESCRIPTION	"Protection 1. level - Active Power - alarm activated"
::= { notifications 16779280 }

tActivePowerL1Disappeared1	NOTIFICATION-TYPE
	OBJECTS	{tControllerName, tSerNum, tTrapText}
	STATUS	current
	DESCRIPTION	"Protection 1. level - Active Power - alarm disappeared"
::= { notifications 16779281 }

tActivePowerL1AlarmReset1	NOTIFICATION-TYPE
	OBJECTS	{tControllerName, tSerNum, tTrapText}
	STATUS	current
	DESCRIPTION	"Protection 1. level - Active Power - alarm reset"
::= { notifications 16779282 }

tActivePowerL2Activated1	NOTIFICATION-TYPE
	OBJECTS	{tControllerName, tSerNum, tTrapText}
	STATUS	current
	DESCRIPTION	"Protection 2. level - Active Power - alarm activated"
::= { notifications 150997008 }

tActivePowerL2Disappeared1	NOTIFICATION-TYPE
	OBJECTS	{tControllerName, tSerNum, tTrapText}
	STATUS	current
	DESCRIPTION	"Protection 2. level - Active Power - alarm disappeared"
::= { notifications 150997009 }

tActivePowerL2AlarmReset1	NOTIFICATION-TYPE
	OBJECTS	{tControllerName, tSerNum, tTrapText}
	STATUS	current
	DESCRIPTION	"Protection 2. level - Active Power - alarm reset"
::= { notifications 150997010 }

tActivePowerSFActivated1	NOTIFICATION-TYPE
	OBJECTS	{tControllerName, tSerNum, tTrapText}
	STATUS	current
	DESCRIPTION	"Protection Sensor Fail - Active Power - alarm activated"
::= { notifications 285214736 }

tActivePowerSFDisappeared1	NOTIFICATION-TYPE
	OBJECTS	{tControllerName, tSerNum, tTrapText}
	STATUS	current
	DESCRIPTION	"Protection Sensor Fail - Active Power - alarm disappeared"
::= { notifications 285214737 }

tActivePowerSFAlarmReset1	NOTIFICATION-TYPE
	OBJECTS	{tControllerName, tSerNum, tTrapText}
	STATUS	current
	DESCRIPTION	"Protection Sensor Fail - Active Power - alarm reset"
::= { notifications 285214738 }

tReactivePowerL1Activated1	NOTIFICATION-TYPE
	OBJECTS	{tControllerName, tSerNum, tTrapText}
	STATUS	current
	DESCRIPTION	"Protection 1. level - Reactive Power - alarm activated"
::= { notifications 16779284 }

tReactivePowerL1Disappeared1	NOTIFICATION-TYPE
	OBJECTS	{tControllerName, tSerNum, tTrapText}
	STATUS	current
	DESCRIPTION	"Protection 1. level - Reactive Power - alarm disappeared"
::= { notifications 16779285 }

tReactivePowerL1AlarmReset1	NOTIFICATION-TYPE
	OBJECTS	{tControllerName, tSerNum, tTrapText}
	STATUS	current
	DESCRIPTION	"Protection 1. level - Reactive Power - alarm reset"
::= { notifications 16779286 }

tReactivePowerL2Activated1	NOTIFICATION-TYPE
	OBJECTS	{tControllerName, tSerNum, tTrapText}
	STATUS	current
	DESCRIPTION	"Protection 2. level - Reactive Power - alarm activated"
::= { notifications 150997012 }

tReactivePowerL2Disappeared1	NOTIFICATION-TYPE
	OBJECTS	{tControllerName, tSerNum, tTrapText}
	STATUS	current
	DESCRIPTION	"Protection 2. level - Reactive Power - alarm disappeared"
::= { notifications 150997013 }

tReactivePowerL2AlarmReset1	NOTIFICATION-TYPE
	OBJECTS	{tControllerName, tSerNum, tTrapText}
	STATUS	current
	DESCRIPTION	"Protection 2. level - Reactive Power - alarm reset"
::= { notifications 150997014 }

tReactivePowerSFActivated1	NOTIFICATION-TYPE
	OBJECTS	{tControllerName, tSerNum, tTrapText}
	STATUS	current
	DESCRIPTION	"Protection Sensor Fail - Reactive Power - alarm activated"
::= { notifications 285214740 }

tReactivePowerSFDisappeared1	NOTIFICATION-TYPE
	OBJECTS	{tControllerName, tSerNum, tTrapText}
	STATUS	current
	DESCRIPTION	"Protection Sensor Fail - Reactive Power - alarm disappeared"
::= { notifications 285214741 }

tReactivePowerSFAlarmReset1	NOTIFICATION-TYPE
	OBJECTS	{tControllerName, tSerNum, tTrapText}
	STATUS	current
	DESCRIPTION	"Protection Sensor Fail - Reactive Power - alarm reset"
::= { notifications 285214742 }

tNominalActivePowerL1Activated	NOTIFICATION-TYPE
	OBJECTS	{tControllerName, tSerNum, tTrapText}
	STATUS	current
	DESCRIPTION	"Protection 1. level - Nominal Active Power - alarm activated"
::= { notifications 16779288 }

tNominalActivePowerL1Disappeared	NOTIFICATION-TYPE
	OBJECTS	{tControllerName, tSerNum, tTrapText}
	STATUS	current
	DESCRIPTION	"Protection 1. level - Nominal Active Power - alarm disappeared"
::= { notifications 16779289 }

tNominalActivePowerL1AlarmReset	NOTIFICATION-TYPE
	OBJECTS	{tControllerName, tSerNum, tTrapText}
	STATUS	current
	DESCRIPTION	"Protection 1. level - Nominal Active Power - alarm reset"
::= { notifications 16779290 }

tNominalActivePowerL2Activated	NOTIFICATION-TYPE
	OBJECTS	{tControllerName, tSerNum, tTrapText}
	STATUS	current
	DESCRIPTION	"Protection 2. level - Nominal Active Power - alarm activated"
::= { notifications 150997016 }

tNominalActivePowerL2Disappeared	NOTIFICATION-TYPE
	OBJECTS	{tControllerName, tSerNum, tTrapText}
	STATUS	current
	DESCRIPTION	"Protection 2. level - Nominal Active Power - alarm disappeared"
::= { notifications 150997017 }

tNominalActivePowerL2AlarmReset	NOTIFICATION-TYPE
	OBJECTS	{tControllerName, tSerNum, tTrapText}
	STATUS	current
	DESCRIPTION	"Protection 2. level - Nominal Active Power - alarm reset"
::= { notifications 150997018 }

tNominalActivePowerSFActivated	NOTIFICATION-TYPE
	OBJECTS	{tControllerName, tSerNum, tTrapText}
	STATUS	current
	DESCRIPTION	"Protection Sensor Fail - Nominal Active Power - alarm activated"
::= { notifications 285214744 }

tNominalActivePowerSFDisappeared	NOTIFICATION-TYPE
	OBJECTS	{tControllerName, tSerNum, tTrapText}
	STATUS	current
	DESCRIPTION	"Protection Sensor Fail - Nominal Active Power - alarm disappeared"
::= { notifications 285214745 }

tNominalActivePowerSFAlarmReset	NOTIFICATION-TYPE
	OBJECTS	{tControllerName, tSerNum, tTrapText}
	STATUS	current
	DESCRIPTION	"Protection Sensor Fail - Nominal Active Power - alarm reset"
::= { notifications 285214746 }

tMaximumActivePowerL1Activated	NOTIFICATION-TYPE
	OBJECTS	{tControllerName, tSerNum, tTrapText}
	STATUS	current
	DESCRIPTION	"Protection 1. level - Maximum Active Power - alarm activated"
::= { notifications 16779292 }

tMaximumActivePowerL1Disappeared	NOTIFICATION-TYPE
	OBJECTS	{tControllerName, tSerNum, tTrapText}
	STATUS	current
	DESCRIPTION	"Protection 1. level - Maximum Active Power - alarm disappeared"
::= { notifications 16779293 }

tMaximumActivePowerL1AlarmReset	NOTIFICATION-TYPE
	OBJECTS	{tControllerName, tSerNum, tTrapText}
	STATUS	current
	DESCRIPTION	"Protection 1. level - Maximum Active Power - alarm reset"
::= { notifications 16779294 }

tMaximumActivePowerL2Activated	NOTIFICATION-TYPE
	OBJECTS	{tControllerName, tSerNum, tTrapText}
	STATUS	current
	DESCRIPTION	"Protection 2. level - Maximum Active Power - alarm activated"
::= { notifications 150997020 }

tMaximumActivePowerL2Disappeared	NOTIFICATION-TYPE
	OBJECTS	{tControllerName, tSerNum, tTrapText}
	STATUS	current
	DESCRIPTION	"Protection 2. level - Maximum Active Power - alarm disappeared"
::= { notifications 150997021 }

tMaximumActivePowerL2AlarmReset	NOTIFICATION-TYPE
	OBJECTS	{tControllerName, tSerNum, tTrapText}
	STATUS	current
	DESCRIPTION	"Protection 2. level - Maximum Active Power - alarm reset"
::= { notifications 150997022 }

tMaximumActivePowerSFActivated	NOTIFICATION-TYPE
	OBJECTS	{tControllerName, tSerNum, tTrapText}
	STATUS	current
	DESCRIPTION	"Protection Sensor Fail - Maximum Active Power - alarm activated"
::= { notifications 285214748 }

tMaximumActivePowerSFDisappeared	NOTIFICATION-TYPE
	OBJECTS	{tControllerName, tSerNum, tTrapText}
	STATUS	current
	DESCRIPTION	"Protection Sensor Fail - Maximum Active Power - alarm disappeared"
::= { notifications 285214749 }

tMaximumActivePowerSFAlarmReset	NOTIFICATION-TYPE
	OBJECTS	{tControllerName, tSerNum, tTrapText}
	STATUS	current
	DESCRIPTION	"Protection Sensor Fail - Maximum Active Power - alarm reset"
::= { notifications 285214750 }

tMaximumApparentPowerL1Activated	NOTIFICATION-TYPE
	OBJECTS	{tControllerName, tSerNum, tTrapText}
	STATUS	current
	DESCRIPTION	"Protection 1. level - Maximum Apparent Power - alarm activated"
::= { notifications 16779296 }

tMaximumApparentPowerL1Disappeared	NOTIFICATION-TYPE
	OBJECTS	{tControllerName, tSerNum, tTrapText}
	STATUS	current
	DESCRIPTION	"Protection 1. level - Maximum Apparent Power - alarm disappeared"
::= { notifications 16779297 }

tMaximumApparentPowerL1AlarmReset	NOTIFICATION-TYPE
	OBJECTS	{tControllerName, tSerNum, tTrapText}
	STATUS	current
	DESCRIPTION	"Protection 1. level - Maximum Apparent Power - alarm reset"
::= { notifications 16779298 }

tMaximumApparentPowerL2Activated	NOTIFICATION-TYPE
	OBJECTS	{tControllerName, tSerNum, tTrapText}
	STATUS	current
	DESCRIPTION	"Protection 2. level - Maximum Apparent Power - alarm activated"
::= { notifications 150997024 }

tMaximumApparentPowerL2Disappeared	NOTIFICATION-TYPE
	OBJECTS	{tControllerName, tSerNum, tTrapText}
	STATUS	current
	DESCRIPTION	"Protection 2. level - Maximum Apparent Power - alarm disappeared"
::= { notifications 150997025 }

tMaximumApparentPowerL2AlarmReset	NOTIFICATION-TYPE
	OBJECTS	{tControllerName, tSerNum, tTrapText}
	STATUS	current
	DESCRIPTION	"Protection 2. level - Maximum Apparent Power - alarm reset"
::= { notifications 150997026 }

tMaximumApparentPowerSFActivated	NOTIFICATION-TYPE
	OBJECTS	{tControllerName, tSerNum, tTrapText}
	STATUS	current
	DESCRIPTION	"Protection Sensor Fail - Maximum Apparent Power - alarm activated"
::= { notifications 285214752 }

tMaximumApparentPowerSFDisappeared	NOTIFICATION-TYPE
	OBJECTS	{tControllerName, tSerNum, tTrapText}
	STATUS	current
	DESCRIPTION	"Protection Sensor Fail - Maximum Apparent Power - alarm disappeared"
::= { notifications 285214753 }

tMaximumApparentPowerSFAlarmReset	NOTIFICATION-TYPE
	OBJECTS	{tControllerName, tSerNum, tTrapText}
	STATUS	current
	DESCRIPTION	"Protection Sensor Fail - Maximum Apparent Power - alarm reset"
::= { notifications 285214754 }

tInputPowerL1Activated	NOTIFICATION-TYPE
	OBJECTS	{tControllerName, tSerNum, tTrapText}
	STATUS	current
	DESCRIPTION	"Protection 1. level - Input Power - alarm activated"
::= { notifications 16779300 }

tInputPowerL1Disappeared	NOTIFICATION-TYPE
	OBJECTS	{tControllerName, tSerNum, tTrapText}
	STATUS	current
	DESCRIPTION	"Protection 1. level - Input Power - alarm disappeared"
::= { notifications 16779301 }

tInputPowerL1AlarmReset	NOTIFICATION-TYPE
	OBJECTS	{tControllerName, tSerNum, tTrapText}
	STATUS	current
	DESCRIPTION	"Protection 1. level - Input Power - alarm reset"
::= { notifications 16779302 }

tInputPowerL2Activated	NOTIFICATION-TYPE
	OBJECTS	{tControllerName, tSerNum, tTrapText}
	STATUS	current
	DESCRIPTION	"Protection 2. level - Input Power - alarm activated"
::= { notifications 150997028 }

tInputPowerL2Disappeared	NOTIFICATION-TYPE
	OBJECTS	{tControllerName, tSerNum, tTrapText}
	STATUS	current
	DESCRIPTION	"Protection 2. level - Input Power - alarm disappeared"
::= { notifications 150997029 }

tInputPowerL2AlarmReset	NOTIFICATION-TYPE
	OBJECTS	{tControllerName, tSerNum, tTrapText}
	STATUS	current
	DESCRIPTION	"Protection 2. level - Input Power - alarm reset"
::= { notifications 150997030 }

tInputPowerSFActivated	NOTIFICATION-TYPE
	OBJECTS	{tControllerName, tSerNum, tTrapText}
	STATUS	current
	DESCRIPTION	"Protection Sensor Fail - Input Power - alarm activated"
::= { notifications 285214756 }

tInputPowerSFDisappeared	NOTIFICATION-TYPE
	OBJECTS	{tControllerName, tSerNum, tTrapText}
	STATUS	current
	DESCRIPTION	"Protection Sensor Fail - Input Power - alarm disappeared"
::= { notifications 285214757 }

tInputPowerSFAlarmReset	NOTIFICATION-TYPE
	OBJECTS	{tControllerName, tSerNum, tTrapText}
	STATUS	current
	DESCRIPTION	"Protection Sensor Fail - Input Power - alarm reset"
::= { notifications 285214758 }

tActivePowerL1Activated2	NOTIFICATION-TYPE
	OBJECTS	{tControllerName, tSerNum, tTrapText}
	STATUS	current
	DESCRIPTION	"Protection 1. level - Active Power - alarm activated"
::= { notifications 16779304 }

tActivePowerL1Disappeared2	NOTIFICATION-TYPE
	OBJECTS	{tControllerName, tSerNum, tTrapText}
	STATUS	current
	DESCRIPTION	"Protection 1. level - Active Power - alarm disappeared"
::= { notifications 16779305 }

tActivePowerL1AlarmReset2	NOTIFICATION-TYPE
	OBJECTS	{tControllerName, tSerNum, tTrapText}
	STATUS	current
	DESCRIPTION	"Protection 1. level - Active Power - alarm reset"
::= { notifications 16779306 }

tActivePowerL2Activated2	NOTIFICATION-TYPE
	OBJECTS	{tControllerName, tSerNum, tTrapText}
	STATUS	current
	DESCRIPTION	"Protection 2. level - Active Power - alarm activated"
::= { notifications 150997032 }

tActivePowerL2Disappeared2	NOTIFICATION-TYPE
	OBJECTS	{tControllerName, tSerNum, tTrapText}
	STATUS	current
	DESCRIPTION	"Protection 2. level - Active Power - alarm disappeared"
::= { notifications 150997033 }

tActivePowerL2AlarmReset2	NOTIFICATION-TYPE
	OBJECTS	{tControllerName, tSerNum, tTrapText}
	STATUS	current
	DESCRIPTION	"Protection 2. level - Active Power - alarm reset"
::= { notifications 150997034 }

tActivePowerSFActivated2	NOTIFICATION-TYPE
	OBJECTS	{tControllerName, tSerNum, tTrapText}
	STATUS	current
	DESCRIPTION	"Protection Sensor Fail - Active Power - alarm activated"
::= { notifications 285214760 }

tActivePowerSFDisappeared2	NOTIFICATION-TYPE
	OBJECTS	{tControllerName, tSerNum, tTrapText}
	STATUS	current
	DESCRIPTION	"Protection Sensor Fail - Active Power - alarm disappeared"
::= { notifications 285214761 }

tActivePowerSFAlarmReset2	NOTIFICATION-TYPE
	OBJECTS	{tControllerName, tSerNum, tTrapText}
	STATUS	current
	DESCRIPTION	"Protection Sensor Fail - Active Power - alarm reset"
::= { notifications 285214762 }

tReactivePowerL1Activated2	NOTIFICATION-TYPE
	OBJECTS	{tControllerName, tSerNum, tTrapText}
	STATUS	current
	DESCRIPTION	"Protection 1. level - Reactive Power - alarm activated"
::= { notifications 16779308 }

tReactivePowerL1Disappeared2	NOTIFICATION-TYPE
	OBJECTS	{tControllerName, tSerNum, tTrapText}
	STATUS	current
	DESCRIPTION	"Protection 1. level - Reactive Power - alarm disappeared"
::= { notifications 16779309 }

tReactivePowerL1AlarmReset2	NOTIFICATION-TYPE
	OBJECTS	{tControllerName, tSerNum, tTrapText}
	STATUS	current
	DESCRIPTION	"Protection 1. level - Reactive Power - alarm reset"
::= { notifications 16779310 }

tReactivePowerL2Activated2	NOTIFICATION-TYPE
	OBJECTS	{tControllerName, tSerNum, tTrapText}
	STATUS	current
	DESCRIPTION	"Protection 2. level - Reactive Power - alarm activated"
::= { notifications 150997036 }

tReactivePowerL2Disappeared2	NOTIFICATION-TYPE
	OBJECTS	{tControllerName, tSerNum, tTrapText}
	STATUS	current
	DESCRIPTION	"Protection 2. level - Reactive Power - alarm disappeared"
::= { notifications 150997037 }

tReactivePowerL2AlarmReset2	NOTIFICATION-TYPE
	OBJECTS	{tControllerName, tSerNum, tTrapText}
	STATUS	current
	DESCRIPTION	"Protection 2. level - Reactive Power - alarm reset"
::= { notifications 150997038 }

tReactivePowerSFActivated2	NOTIFICATION-TYPE
	OBJECTS	{tControllerName, tSerNum, tTrapText}
	STATUS	current
	DESCRIPTION	"Protection Sensor Fail - Reactive Power - alarm activated"
::= { notifications 285214764 }

tReactivePowerSFDisappeared2	NOTIFICATION-TYPE
	OBJECTS	{tControllerName, tSerNum, tTrapText}
	STATUS	current
	DESCRIPTION	"Protection Sensor Fail - Reactive Power - alarm disappeared"
::= { notifications 285214765 }

tReactivePowerSFAlarmReset2	NOTIFICATION-TYPE
	OBJECTS	{tControllerName, tSerNum, tTrapText}
	STATUS	current
	DESCRIPTION	"Protection Sensor Fail - Reactive Power - alarm reset"
::= { notifications 285214766 }

tRealTimeActivePowerPercentL1Activated	NOTIFICATION-TYPE
	OBJECTS	{tControllerName, tSerNum, tTrapText}
	STATUS	current
	DESCRIPTION	"Protection 1. level - Real-time active power % - alarm activated"
::= { notifications 16779312 }

tRealTimeActivePowerPercentL1Disappeared	NOTIFICATION-TYPE
	OBJECTS	{tControllerName, tSerNum, tTrapText}
	STATUS	current
	DESCRIPTION	"Protection 1. level - Real-time active power % - alarm disappeared"
::= { notifications 16779313 }

tRealTimeActivePowerPercentL1AlarmReset	NOTIFICATION-TYPE
	OBJECTS	{tControllerName, tSerNum, tTrapText}
	STATUS	current
	DESCRIPTION	"Protection 1. level - Real-time active power % - alarm reset"
::= { notifications 16779314 }

tRealTimeActivePowerPercentL2Activated	NOTIFICATION-TYPE
	OBJECTS	{tControllerName, tSerNum, tTrapText}
	STATUS	current
	DESCRIPTION	"Protection 2. level - Real-time active power % - alarm activated"
::= { notifications 150997040 }

tRealTimeActivePowerPercentL2Disappeared	NOTIFICATION-TYPE
	OBJECTS	{tControllerName, tSerNum, tTrapText}
	STATUS	current
	DESCRIPTION	"Protection 2. level - Real-time active power % - alarm disappeared"
::= { notifications 150997041 }

tRealTimeActivePowerPercentL2AlarmReset	NOTIFICATION-TYPE
	OBJECTS	{tControllerName, tSerNum, tTrapText}
	STATUS	current
	DESCRIPTION	"Protection 2. level - Real-time active power % - alarm reset"
::= { notifications 150997042 }

tRealTimeActivePowerPercentSFActivated	NOTIFICATION-TYPE
	OBJECTS	{tControllerName, tSerNum, tTrapText}
	STATUS	current
	DESCRIPTION	"Protection Sensor Fail - Real-time active power % - alarm activated"
::= { notifications 285214768 }

tRealTimeActivePowerPercentSFDisappeared	NOTIFICATION-TYPE
	OBJECTS	{tControllerName, tSerNum, tTrapText}
	STATUS	current
	DESCRIPTION	"Protection Sensor Fail - Real-time active power % - alarm disappeared"
::= { notifications 285214769 }

tRealTimeActivePowerPercentSFAlarmReset	NOTIFICATION-TYPE
	OBJECTS	{tControllerName, tSerNum, tTrapText}
	STATUS	current
	DESCRIPTION	"Protection Sensor Fail - Real-time active power % - alarm reset"
::= { notifications 285214770 }

tREACTPercentL1Activated1	NOTIFICATION-TYPE
	OBJECTS	{tControllerName, tSerNum, tTrapText}
	STATUS	current
	DESCRIPTION	"Protection 1. level - REACT % - alarm activated"
::= { notifications 16779316 }

tREACTPercentL1Disappeared1	NOTIFICATION-TYPE
	OBJECTS	{tControllerName, tSerNum, tTrapText}
	STATUS	current
	DESCRIPTION	"Protection 1. level - REACT % - alarm disappeared"
::= { notifications 16779317 }

tREACTPercentL1AlarmReset1	NOTIFICATION-TYPE
	OBJECTS	{tControllerName, tSerNum, tTrapText}
	STATUS	current
	DESCRIPTION	"Protection 1. level - REACT % - alarm reset"
::= { notifications 16779318 }

tREACTPercentL2Activated1	NOTIFICATION-TYPE
	OBJECTS	{tControllerName, tSerNum, tTrapText}
	STATUS	current
	DESCRIPTION	"Protection 2. level - REACT % - alarm activated"
::= { notifications 150997044 }

tREACTPercentL2Disappeared1	NOTIFICATION-TYPE
	OBJECTS	{tControllerName, tSerNum, tTrapText}
	STATUS	current
	DESCRIPTION	"Protection 2. level - REACT % - alarm disappeared"
::= { notifications 150997045 }

tREACTPercentL2AlarmReset1	NOTIFICATION-TYPE
	OBJECTS	{tControllerName, tSerNum, tTrapText}
	STATUS	current
	DESCRIPTION	"Protection 2. level - REACT % - alarm reset"
::= { notifications 150997046 }

tREACTPercentSFActivated1	NOTIFICATION-TYPE
	OBJECTS	{tControllerName, tSerNum, tTrapText}
	STATUS	current
	DESCRIPTION	"Protection Sensor Fail - REACT % - alarm activated"
::= { notifications 285214772 }

tREACTPercentSFDisappeared1	NOTIFICATION-TYPE
	OBJECTS	{tControllerName, tSerNum, tTrapText}
	STATUS	current
	DESCRIPTION	"Protection Sensor Fail - REACT % - alarm disappeared"
::= { notifications 285214773 }

tREACTPercentSFAlarmReset1	NOTIFICATION-TYPE
	OBJECTS	{tControllerName, tSerNum, tTrapText}
	STATUS	current
	DESCRIPTION	"Protection Sensor Fail - REACT % - alarm reset"
::= { notifications 285214774 }

tPFSETL1Activated	NOTIFICATION-TYPE
	OBJECTS	{tControllerName, tSerNum, tTrapText}
	STATUS	current
	DESCRIPTION	"Protection 1. level - PF SET - alarm activated"
::= { notifications 16779320 }

tPFSETL1Disappeared	NOTIFICATION-TYPE
	OBJECTS	{tControllerName, tSerNum, tTrapText}
	STATUS	current
	DESCRIPTION	"Protection 1. level - PF SET - alarm disappeared"
::= { notifications 16779321 }

tPFSETL1AlarmReset	NOTIFICATION-TYPE
	OBJECTS	{tControllerName, tSerNum, tTrapText}
	STATUS	current
	DESCRIPTION	"Protection 1. level - PF SET - alarm reset"
::= { notifications 16779322 }

tPFSETL2Activated	NOTIFICATION-TYPE
	OBJECTS	{tControllerName, tSerNum, tTrapText}
	STATUS	current
	DESCRIPTION	"Protection 2. level - PF SET - alarm activated"
::= { notifications 150997048 }

tPFSETL2Disappeared	NOTIFICATION-TYPE
	OBJECTS	{tControllerName, tSerNum, tTrapText}
	STATUS	current
	DESCRIPTION	"Protection 2. level - PF SET - alarm disappeared"
::= { notifications 150997049 }

tPFSETL2AlarmReset	NOTIFICATION-TYPE
	OBJECTS	{tControllerName, tSerNum, tTrapText}
	STATUS	current
	DESCRIPTION	"Protection 2. level - PF SET - alarm reset"
::= { notifications 150997050 }

tPFSETSFActivated	NOTIFICATION-TYPE
	OBJECTS	{tControllerName, tSerNum, tTrapText}
	STATUS	current
	DESCRIPTION	"Protection Sensor Fail - PF SET - alarm activated"
::= { notifications 285214776 }

tPFSETSFDisappeared	NOTIFICATION-TYPE
	OBJECTS	{tControllerName, tSerNum, tTrapText}
	STATUS	current
	DESCRIPTION	"Protection Sensor Fail - PF SET - alarm disappeared"
::= { notifications 285214777 }

tPFSETSFAlarmReset	NOTIFICATION-TYPE
	OBJECTS	{tControllerName, tSerNum, tTrapText}
	STATUS	current
	DESCRIPTION	"Protection Sensor Fail - PF SET - alarm reset"
::= { notifications 285214778 }

tTOTKWhPV2L1Activated	NOTIFICATION-TYPE
	OBJECTS	{tControllerName, tSerNum, tTrapText}
	STATUS	current
	DESCRIPTION	"Protection 1. level - TOT kWh PV 2 - alarm activated"
::= { notifications 16779324 }

tTOTKWhPV2L1Disappeared	NOTIFICATION-TYPE
	OBJECTS	{tControllerName, tSerNum, tTrapText}
	STATUS	current
	DESCRIPTION	"Protection 1. level - TOT kWh PV 2 - alarm disappeared"
::= { notifications 16779325 }

tTOTKWhPV2L1AlarmReset	NOTIFICATION-TYPE
	OBJECTS	{tControllerName, tSerNum, tTrapText}
	STATUS	current
	DESCRIPTION	"Protection 1. level - TOT kWh PV 2 - alarm reset"
::= { notifications 16779326 }

tTOTKWhPV2L2Activated	NOTIFICATION-TYPE
	OBJECTS	{tControllerName, tSerNum, tTrapText}
	STATUS	current
	DESCRIPTION	"Protection 2. level - TOT kWh PV 2 - alarm activated"
::= { notifications 150997052 }

tTOTKWhPV2L2Disappeared	NOTIFICATION-TYPE
	OBJECTS	{tControllerName, tSerNum, tTrapText}
	STATUS	current
	DESCRIPTION	"Protection 2. level - TOT kWh PV 2 - alarm disappeared"
::= { notifications 150997053 }

tTOTKWhPV2L2AlarmReset	NOTIFICATION-TYPE
	OBJECTS	{tControllerName, tSerNum, tTrapText}
	STATUS	current
	DESCRIPTION	"Protection 2. level - TOT kWh PV 2 - alarm reset"
::= { notifications 150997054 }

tTOTKWhPV2SFActivated	NOTIFICATION-TYPE
	OBJECTS	{tControllerName, tSerNum, tTrapText}
	STATUS	current
	DESCRIPTION	"Protection Sensor Fail - TOT kWh PV 2 - alarm activated"
::= { notifications 285214780 }

tTOTKWhPV2SFDisappeared	NOTIFICATION-TYPE
	OBJECTS	{tControllerName, tSerNum, tTrapText}
	STATUS	current
	DESCRIPTION	"Protection Sensor Fail - TOT kWh PV 2 - alarm disappeared"
::= { notifications 285214781 }

tTOTKWhPV2SFAlarmReset	NOTIFICATION-TYPE
	OBJECTS	{tControllerName, tSerNum, tTrapText}
	STATUS	current
	DESCRIPTION	"Protection Sensor Fail - TOT kWh PV 2 - alarm reset"
::= { notifications 285214782 }

tTOTKWhPV1L1Activated	NOTIFICATION-TYPE
	OBJECTS	{tControllerName, tSerNum, tTrapText}
	STATUS	current
	DESCRIPTION	"Protection 1. level - TOT kWh PV 1 - alarm activated"
::= { notifications 16779328 }

tTOTKWhPV1L1Disappeared	NOTIFICATION-TYPE
	OBJECTS	{tControllerName, tSerNum, tTrapText}
	STATUS	current
	DESCRIPTION	"Protection 1. level - TOT kWh PV 1 - alarm disappeared"
::= { notifications 16779329 }

tTOTKWhPV1L1AlarmReset	NOTIFICATION-TYPE
	OBJECTS	{tControllerName, tSerNum, tTrapText}
	STATUS	current
	DESCRIPTION	"Protection 1. level - TOT kWh PV 1 - alarm reset"
::= { notifications 16779330 }

tTOTKWhPV1L2Activated	NOTIFICATION-TYPE
	OBJECTS	{tControllerName, tSerNum, tTrapText}
	STATUS	current
	DESCRIPTION	"Protection 2. level - TOT kWh PV 1 - alarm activated"
::= { notifications 150997056 }

tTOTKWhPV1L2Disappeared	NOTIFICATION-TYPE
	OBJECTS	{tControllerName, tSerNum, tTrapText}
	STATUS	current
	DESCRIPTION	"Protection 2. level - TOT kWh PV 1 - alarm disappeared"
::= { notifications 150997057 }

tTOTKWhPV1L2AlarmReset	NOTIFICATION-TYPE
	OBJECTS	{tControllerName, tSerNum, tTrapText}
	STATUS	current
	DESCRIPTION	"Protection 2. level - TOT kWh PV 1 - alarm reset"
::= { notifications 150997058 }

tTOTKWhPV1SFActivated	NOTIFICATION-TYPE
	OBJECTS	{tControllerName, tSerNum, tTrapText}
	STATUS	current
	DESCRIPTION	"Protection Sensor Fail - TOT kWh PV 1 - alarm activated"
::= { notifications 285214784 }

tTOTKWhPV1SFDisappeared	NOTIFICATION-TYPE
	OBJECTS	{tControllerName, tSerNum, tTrapText}
	STATUS	current
	DESCRIPTION	"Protection Sensor Fail - TOT kWh PV 1 - alarm disappeared"
::= { notifications 285214785 }

tTOTKWhPV1SFAlarmReset	NOTIFICATION-TYPE
	OBJECTS	{tControllerName, tSerNum, tTrapText}
	STATUS	current
	DESCRIPTION	"Protection Sensor Fail - TOT kWh PV 1 - alarm reset"
::= { notifications 285214786 }

tACTPOWERL1Activated	NOTIFICATION-TYPE
	OBJECTS	{tControllerName, tSerNum, tTrapText}
	STATUS	current
	DESCRIPTION	"Protection 1. level - ACT POWER - alarm activated"
::= { notifications 16779332 }

tACTPOWERL1Disappeared	NOTIFICATION-TYPE
	OBJECTS	{tControllerName, tSerNum, tTrapText}
	STATUS	current
	DESCRIPTION	"Protection 1. level - ACT POWER - alarm disappeared"
::= { notifications 16779333 }

tACTPOWERL1AlarmReset	NOTIFICATION-TYPE
	OBJECTS	{tControllerName, tSerNum, tTrapText}
	STATUS	current
	DESCRIPTION	"Protection 1. level - ACT POWER - alarm reset"
::= { notifications 16779334 }

tACTPOWERL2Activated	NOTIFICATION-TYPE
	OBJECTS	{tControllerName, tSerNum, tTrapText}
	STATUS	current
	DESCRIPTION	"Protection 2. level - ACT POWER - alarm activated"
::= { notifications 150997060 }

tACTPOWERL2Disappeared	NOTIFICATION-TYPE
	OBJECTS	{tControllerName, tSerNum, tTrapText}
	STATUS	current
	DESCRIPTION	"Protection 2. level - ACT POWER - alarm disappeared"
::= { notifications 150997061 }

tACTPOWERL2AlarmReset	NOTIFICATION-TYPE
	OBJECTS	{tControllerName, tSerNum, tTrapText}
	STATUS	current
	DESCRIPTION	"Protection 2. level - ACT POWER - alarm reset"
::= { notifications 150997062 }

tACTPOWERSFActivated	NOTIFICATION-TYPE
	OBJECTS	{tControllerName, tSerNum, tTrapText}
	STATUS	current
	DESCRIPTION	"Protection Sensor Fail - ACT POWER - alarm activated"
::= { notifications 285214788 }

tACTPOWERSFDisappeared	NOTIFICATION-TYPE
	OBJECTS	{tControllerName, tSerNum, tTrapText}
	STATUS	current
	DESCRIPTION	"Protection Sensor Fail - ACT POWER - alarm disappeared"
::= { notifications 285214789 }

tACTPOWERSFAlarmReset	NOTIFICATION-TYPE
	OBJECTS	{tControllerName, tSerNum, tTrapText}
	STATUS	current
	DESCRIPTION	"Protection Sensor Fail - ACT POWER - alarm reset"
::= { notifications 285214790 }

tREACTPercentL1Activated2	NOTIFICATION-TYPE
	OBJECTS	{tControllerName, tSerNum, tTrapText}
	STATUS	current
	DESCRIPTION	"Protection 1. level - REACT % - alarm activated"
::= { notifications 16779336 }

tREACTPercentL1Disappeared2	NOTIFICATION-TYPE
	OBJECTS	{tControllerName, tSerNum, tTrapText}
	STATUS	current
	DESCRIPTION	"Protection 1. level - REACT % - alarm disappeared"
::= { notifications 16779337 }

tREACTPercentL1AlarmReset2	NOTIFICATION-TYPE
	OBJECTS	{tControllerName, tSerNum, tTrapText}
	STATUS	current
	DESCRIPTION	"Protection 1. level - REACT % - alarm reset"
::= { notifications 16779338 }

tREACTPercentL2Activated2	NOTIFICATION-TYPE
	OBJECTS	{tControllerName, tSerNum, tTrapText}
	STATUS	current
	DESCRIPTION	"Protection 2. level - REACT % - alarm activated"
::= { notifications 150997064 }

tREACTPercentL2Disappeared2	NOTIFICATION-TYPE
	OBJECTS	{tControllerName, tSerNum, tTrapText}
	STATUS	current
	DESCRIPTION	"Protection 2. level - REACT % - alarm disappeared"
::= { notifications 150997065 }

tREACTPercentL2AlarmReset2	NOTIFICATION-TYPE
	OBJECTS	{tControllerName, tSerNum, tTrapText}
	STATUS	current
	DESCRIPTION	"Protection 2. level - REACT % - alarm reset"
::= { notifications 150997066 }

tREACTPercentSFActivated2	NOTIFICATION-TYPE
	OBJECTS	{tControllerName, tSerNum, tTrapText}
	STATUS	current
	DESCRIPTION	"Protection Sensor Fail - REACT % - alarm activated"
::= { notifications 285214792 }

tREACTPercentSFDisappeared2	NOTIFICATION-TYPE
	OBJECTS	{tControllerName, tSerNum, tTrapText}
	STATUS	current
	DESCRIPTION	"Protection Sensor Fail - REACT % - alarm disappeared"
::= { notifications 285214793 }

tREACTPercentSFAlarmReset2	NOTIFICATION-TYPE
	OBJECTS	{tControllerName, tSerNum, tTrapText}
	STATUS	current
	DESCRIPTION	"Protection Sensor Fail - REACT % - alarm reset"
::= { notifications 285214794 }

tREACTPOWERL1Activated	NOTIFICATION-TYPE
	OBJECTS	{tControllerName, tSerNum, tTrapText}
	STATUS	current
	DESCRIPTION	"Protection 1. level - REACT POWER - alarm activated"
::= { notifications 16779340 }

tREACTPOWERL1Disappeared	NOTIFICATION-TYPE
	OBJECTS	{tControllerName, tSerNum, tTrapText}
	STATUS	current
	DESCRIPTION	"Protection 1. level - REACT POWER - alarm disappeared"
::= { notifications 16779341 }

tREACTPOWERL1AlarmReset	NOTIFICATION-TYPE
	OBJECTS	{tControllerName, tSerNum, tTrapText}
	STATUS	current
	DESCRIPTION	"Protection 1. level - REACT POWER - alarm reset"
::= { notifications 16779342 }

tREACTPOWERL2Activated	NOTIFICATION-TYPE
	OBJECTS	{tControllerName, tSerNum, tTrapText}
	STATUS	current
	DESCRIPTION	"Protection 2. level - REACT POWER - alarm activated"
::= { notifications 150997068 }

tREACTPOWERL2Disappeared	NOTIFICATION-TYPE
	OBJECTS	{tControllerName, tSerNum, tTrapText}
	STATUS	current
	DESCRIPTION	"Protection 2. level - REACT POWER - alarm disappeared"
::= { notifications 150997069 }

tREACTPOWERL2AlarmReset	NOTIFICATION-TYPE
	OBJECTS	{tControllerName, tSerNum, tTrapText}
	STATUS	current
	DESCRIPTION	"Protection 2. level - REACT POWER - alarm reset"
::= { notifications 150997070 }

tREACTPOWERSFActivated	NOTIFICATION-TYPE
	OBJECTS	{tControllerName, tSerNum, tTrapText}
	STATUS	current
	DESCRIPTION	"Protection Sensor Fail - REACT POWER - alarm activated"
::= { notifications 285214796 }

tREACTPOWERSFDisappeared	NOTIFICATION-TYPE
	OBJECTS	{tControllerName, tSerNum, tTrapText}
	STATUS	current
	DESCRIPTION	"Protection Sensor Fail - REACT POWER - alarm disappeared"
::= { notifications 285214797 }

tREACTPOWERSFAlarmReset	NOTIFICATION-TYPE
	OBJECTS	{tControllerName, tSerNum, tTrapText}
	STATUS	current
	DESCRIPTION	"Protection Sensor Fail - REACT POWER - alarm reset"
::= { notifications 285214798 }

tACTNRJIMPORTL1Activated	NOTIFICATION-TYPE
	OBJECTS	{tControllerName, tSerNum, tTrapText}
	STATUS	current
	DESCRIPTION	"Protection 1. level - ACT NRJ IMPORT - alarm activated"
::= { notifications 16779344 }

tACTNRJIMPORTL1Disappeared	NOTIFICATION-TYPE
	OBJECTS	{tControllerName, tSerNum, tTrapText}
	STATUS	current
	DESCRIPTION	"Protection 1. level - ACT NRJ IMPORT - alarm disappeared"
::= { notifications 16779345 }

tACTNRJIMPORTL1AlarmReset	NOTIFICATION-TYPE
	OBJECTS	{tControllerName, tSerNum, tTrapText}
	STATUS	current
	DESCRIPTION	"Protection 1. level - ACT NRJ IMPORT - alarm reset"
::= { notifications 16779346 }

tACTNRJIMPORTL2Activated	NOTIFICATION-TYPE
	OBJECTS	{tControllerName, tSerNum, tTrapText}
	STATUS	current
	DESCRIPTION	"Protection 2. level - ACT NRJ IMPORT - alarm activated"
::= { notifications 150997072 }

tACTNRJIMPORTL2Disappeared	NOTIFICATION-TYPE
	OBJECTS	{tControllerName, tSerNum, tTrapText}
	STATUS	current
	DESCRIPTION	"Protection 2. level - ACT NRJ IMPORT - alarm disappeared"
::= { notifications 150997073 }

tACTNRJIMPORTL2AlarmReset	NOTIFICATION-TYPE
	OBJECTS	{tControllerName, tSerNum, tTrapText}
	STATUS	current
	DESCRIPTION	"Protection 2. level - ACT NRJ IMPORT - alarm reset"
::= { notifications 150997074 }

tACTNRJIMPORTSFActivated	NOTIFICATION-TYPE
	OBJECTS	{tControllerName, tSerNum, tTrapText}
	STATUS	current
	DESCRIPTION	"Protection Sensor Fail - ACT NRJ IMPORT - alarm activated"
::= { notifications 285214800 }

tACTNRJIMPORTSFDisappeared	NOTIFICATION-TYPE
	OBJECTS	{tControllerName, tSerNum, tTrapText}
	STATUS	current
	DESCRIPTION	"Protection Sensor Fail - ACT NRJ IMPORT - alarm disappeared"
::= { notifications 285214801 }

tACTNRJIMPORTSFAlarmReset	NOTIFICATION-TYPE
	OBJECTS	{tControllerName, tSerNum, tTrapText}
	STATUS	current
	DESCRIPTION	"Protection Sensor Fail - ACT NRJ IMPORT - alarm reset"
::= { notifications 285214802 }

tACTNRJEXPORTL1Activated	NOTIFICATION-TYPE
	OBJECTS	{tControllerName, tSerNum, tTrapText}
	STATUS	current
	DESCRIPTION	"Protection 1. level - ACT NRJ EXPORT - alarm activated"
::= { notifications 16779348 }

tACTNRJEXPORTL1Disappeared	NOTIFICATION-TYPE
	OBJECTS	{tControllerName, tSerNum, tTrapText}
	STATUS	current
	DESCRIPTION	"Protection 1. level - ACT NRJ EXPORT - alarm disappeared"
::= { notifications 16779349 }

tACTNRJEXPORTL1AlarmReset	NOTIFICATION-TYPE
	OBJECTS	{tControllerName, tSerNum, tTrapText}
	STATUS	current
	DESCRIPTION	"Protection 1. level - ACT NRJ EXPORT - alarm reset"
::= { notifications 16779350 }

tACTNRJEXPORTL2Activated	NOTIFICATION-TYPE
	OBJECTS	{tControllerName, tSerNum, tTrapText}
	STATUS	current
	DESCRIPTION	"Protection 2. level - ACT NRJ EXPORT - alarm activated"
::= { notifications 150997076 }

tACTNRJEXPORTL2Disappeared	NOTIFICATION-TYPE
	OBJECTS	{tControllerName, tSerNum, tTrapText}
	STATUS	current
	DESCRIPTION	"Protection 2. level - ACT NRJ EXPORT - alarm disappeared"
::= { notifications 150997077 }

tACTNRJEXPORTL2AlarmReset	NOTIFICATION-TYPE
	OBJECTS	{tControllerName, tSerNum, tTrapText}
	STATUS	current
	DESCRIPTION	"Protection 2. level - ACT NRJ EXPORT - alarm reset"
::= { notifications 150997078 }

tACTNRJEXPORTSFActivated	NOTIFICATION-TYPE
	OBJECTS	{tControllerName, tSerNum, tTrapText}
	STATUS	current
	DESCRIPTION	"Protection Sensor Fail - ACT NRJ EXPORT - alarm activated"
::= { notifications 285214804 }

tACTNRJEXPORTSFDisappeared	NOTIFICATION-TYPE
	OBJECTS	{tControllerName, tSerNum, tTrapText}
	STATUS	current
	DESCRIPTION	"Protection Sensor Fail - ACT NRJ EXPORT - alarm disappeared"
::= { notifications 285214805 }

tACTNRJEXPORTSFAlarmReset	NOTIFICATION-TYPE
	OBJECTS	{tControllerName, tSerNum, tTrapText}
	STATUS	current
	DESCRIPTION	"Protection Sensor Fail - ACT NRJ EXPORT - alarm reset"
::= { notifications 285214806 }

tAbsorbedEnergyL1Activated	NOTIFICATION-TYPE
	OBJECTS	{tControllerName, tSerNum, tTrapText}
	STATUS	current
	DESCRIPTION	"Protection 1. level - Absorbed Energy - alarm activated"
::= { notifications 16779352 }

tAbsorbedEnergyL1Disappeared	NOTIFICATION-TYPE
	OBJECTS	{tControllerName, tSerNum, tTrapText}
	STATUS	current
	DESCRIPTION	"Protection 1. level - Absorbed Energy - alarm disappeared"
::= { notifications 16779353 }

tAbsorbedEnergyL1AlarmReset	NOTIFICATION-TYPE
	OBJECTS	{tControllerName, tSerNum, tTrapText}
	STATUS	current
	DESCRIPTION	"Protection 1. level - Absorbed Energy - alarm reset"
::= { notifications 16779354 }

tAbsorbedEnergyL2Activated	NOTIFICATION-TYPE
	OBJECTS	{tControllerName, tSerNum, tTrapText}
	STATUS	current
	DESCRIPTION	"Protection 2. level - Absorbed Energy - alarm activated"
::= { notifications 150997080 }

tAbsorbedEnergyL2Disappeared	NOTIFICATION-TYPE
	OBJECTS	{tControllerName, tSerNum, tTrapText}
	STATUS	current
	DESCRIPTION	"Protection 2. level - Absorbed Energy - alarm disappeared"
::= { notifications 150997081 }

tAbsorbedEnergyL2AlarmReset	NOTIFICATION-TYPE
	OBJECTS	{tControllerName, tSerNum, tTrapText}
	STATUS	current
	DESCRIPTION	"Protection 2. level - Absorbed Energy - alarm reset"
::= { notifications 150997082 }

tAbsorbedEnergySFActivated	NOTIFICATION-TYPE
	OBJECTS	{tControllerName, tSerNum, tTrapText}
	STATUS	current
	DESCRIPTION	"Protection Sensor Fail - Absorbed Energy - alarm activated"
::= { notifications 285214808 }

tAbsorbedEnergySFDisappeared	NOTIFICATION-TYPE
	OBJECTS	{tControllerName, tSerNum, tTrapText}
	STATUS	current
	DESCRIPTION	"Protection Sensor Fail - Absorbed Energy - alarm disappeared"
::= { notifications 285214809 }

tAbsorbedEnergySFAlarmReset	NOTIFICATION-TYPE
	OBJECTS	{tControllerName, tSerNum, tTrapText}
	STATUS	current
	DESCRIPTION	"Protection Sensor Fail - Absorbed Energy - alarm reset"
::= { notifications 285214810 }

tReleasedEnergyL1Activated	NOTIFICATION-TYPE
	OBJECTS	{tControllerName, tSerNum, tTrapText}
	STATUS	current
	DESCRIPTION	"Protection 1. level - Released Energy - alarm activated"
::= { notifications 16779356 }

tReleasedEnergyL1Disappeared	NOTIFICATION-TYPE
	OBJECTS	{tControllerName, tSerNum, tTrapText}
	STATUS	current
	DESCRIPTION	"Protection 1. level - Released Energy - alarm disappeared"
::= { notifications 16779357 }

tReleasedEnergyL1AlarmReset	NOTIFICATION-TYPE
	OBJECTS	{tControllerName, tSerNum, tTrapText}
	STATUS	current
	DESCRIPTION	"Protection 1. level - Released Energy - alarm reset"
::= { notifications 16779358 }

tReleasedEnergyL2Activated	NOTIFICATION-TYPE
	OBJECTS	{tControllerName, tSerNum, tTrapText}
	STATUS	current
	DESCRIPTION	"Protection 2. level - Released Energy - alarm activated"
::= { notifications 150997084 }

tReleasedEnergyL2Disappeared	NOTIFICATION-TYPE
	OBJECTS	{tControllerName, tSerNum, tTrapText}
	STATUS	current
	DESCRIPTION	"Protection 2. level - Released Energy - alarm disappeared"
::= { notifications 150997085 }

tReleasedEnergyL2AlarmReset	NOTIFICATION-TYPE
	OBJECTS	{tControllerName, tSerNum, tTrapText}
	STATUS	current
	DESCRIPTION	"Protection 2. level - Released Energy - alarm reset"
::= { notifications 150997086 }

tReleasedEnergySFActivated	NOTIFICATION-TYPE
	OBJECTS	{tControllerName, tSerNum, tTrapText}
	STATUS	current
	DESCRIPTION	"Protection Sensor Fail - Released Energy - alarm activated"
::= { notifications 285214812 }

tReleasedEnergySFDisappeared	NOTIFICATION-TYPE
	OBJECTS	{tControllerName, tSerNum, tTrapText}
	STATUS	current
	DESCRIPTION	"Protection Sensor Fail - Released Energy - alarm disappeared"
::= { notifications 285214813 }

tReleasedEnergySFAlarmReset	NOTIFICATION-TYPE
	OBJECTS	{tControllerName, tSerNum, tTrapText}
	STATUS	current
	DESCRIPTION	"Protection Sensor Fail - Released Energy - alarm reset"
::= { notifications 285214814 }

tSOCL1Activated	NOTIFICATION-TYPE
	OBJECTS	{tControllerName, tSerNum, tTrapText}
	STATUS	current
	DESCRIPTION	"Protection 1. level - SOC - alarm activated"
::= { notifications 16779368 }

tSOCL1Disappeared	NOTIFICATION-TYPE
	OBJECTS	{tControllerName, tSerNum, tTrapText}
	STATUS	current
	DESCRIPTION	"Protection 1. level - SOC - alarm disappeared"
::= { notifications 16779369 }

tSOCL1AlarmReset	NOTIFICATION-TYPE
	OBJECTS	{tControllerName, tSerNum, tTrapText}
	STATUS	current
	DESCRIPTION	"Protection 1. level - SOC - alarm reset"
::= { notifications 16779370 }

tSOCL2Activated	NOTIFICATION-TYPE
	OBJECTS	{tControllerName, tSerNum, tTrapText}
	STATUS	current
	DESCRIPTION	"Protection 2. level - SOC - alarm activated"
::= { notifications 150997096 }

tSOCL2Disappeared	NOTIFICATION-TYPE
	OBJECTS	{tControllerName, tSerNum, tTrapText}
	STATUS	current
	DESCRIPTION	"Protection 2. level - SOC - alarm disappeared"
::= { notifications 150997097 }

tSOCL2AlarmReset	NOTIFICATION-TYPE
	OBJECTS	{tControllerName, tSerNum, tTrapText}
	STATUS	current
	DESCRIPTION	"Protection 2. level - SOC - alarm reset"
::= { notifications 150997098 }

tSOCSFActivated	NOTIFICATION-TYPE
	OBJECTS	{tControllerName, tSerNum, tTrapText}
	STATUS	current
	DESCRIPTION	"Protection Sensor Fail - SOC - alarm activated"
::= { notifications 285214824 }

tSOCSFDisappeared	NOTIFICATION-TYPE
	OBJECTS	{tControllerName, tSerNum, tTrapText}
	STATUS	current
	DESCRIPTION	"Protection Sensor Fail - SOC - alarm disappeared"
::= { notifications 285214825 }

tSOCSFAlarmReset	NOTIFICATION-TYPE
	OBJECTS	{tControllerName, tSerNum, tTrapText}
	STATUS	current
	DESCRIPTION	"Protection Sensor Fail - SOC - alarm reset"
::= { notifications 285214826 }

tSOHL1Activated	NOTIFICATION-TYPE
	OBJECTS	{tControllerName, tSerNum, tTrapText}
	STATUS	current
	DESCRIPTION	"Protection 1. level - SOH - alarm activated"
::= { notifications 16779372 }

tSOHL1Disappeared	NOTIFICATION-TYPE
	OBJECTS	{tControllerName, tSerNum, tTrapText}
	STATUS	current
	DESCRIPTION	"Protection 1. level - SOH - alarm disappeared"
::= { notifications 16779373 }

tSOHL1AlarmReset	NOTIFICATION-TYPE
	OBJECTS	{tControllerName, tSerNum, tTrapText}
	STATUS	current
	DESCRIPTION	"Protection 1. level - SOH - alarm reset"
::= { notifications 16779374 }

tSOHL2Activated	NOTIFICATION-TYPE
	OBJECTS	{tControllerName, tSerNum, tTrapText}
	STATUS	current
	DESCRIPTION	"Protection 2. level - SOH - alarm activated"
::= { notifications 150997100 }

tSOHL2Disappeared	NOTIFICATION-TYPE
	OBJECTS	{tControllerName, tSerNum, tTrapText}
	STATUS	current
	DESCRIPTION	"Protection 2. level - SOH - alarm disappeared"
::= { notifications 150997101 }

tSOHL2AlarmReset	NOTIFICATION-TYPE
	OBJECTS	{tControllerName, tSerNum, tTrapText}
	STATUS	current
	DESCRIPTION	"Protection 2. level - SOH - alarm reset"
::= { notifications 150997102 }

tSOHSFActivated	NOTIFICATION-TYPE
	OBJECTS	{tControllerName, tSerNum, tTrapText}
	STATUS	current
	DESCRIPTION	"Protection Sensor Fail - SOH - alarm activated"
::= { notifications 285214828 }

tSOHSFDisappeared	NOTIFICATION-TYPE
	OBJECTS	{tControllerName, tSerNum, tTrapText}
	STATUS	current
	DESCRIPTION	"Protection Sensor Fail - SOH - alarm disappeared"
::= { notifications 285214829 }

tSOHSFAlarmReset	NOTIFICATION-TYPE
	OBJECTS	{tControllerName, tSerNum, tTrapText}
	STATUS	current
	DESCRIPTION	"Protection Sensor Fail - SOH - alarm reset"
::= { notifications 285214830 }

tCurrentL1L1Activated	NOTIFICATION-TYPE
	OBJECTS	{tControllerName, tSerNum, tTrapText}
	STATUS	current
	DESCRIPTION	"Protection 1. level - Current L1 - alarm activated"
::= { notifications 16779380 }

tCurrentL1L1Disappeared	NOTIFICATION-TYPE
	OBJECTS	{tControllerName, tSerNum, tTrapText}
	STATUS	current
	DESCRIPTION	"Protection 1. level - Current L1 - alarm disappeared"
::= { notifications 16779381 }

tCurrentL1L1AlarmReset	NOTIFICATION-TYPE
	OBJECTS	{tControllerName, tSerNum, tTrapText}
	STATUS	current
	DESCRIPTION	"Protection 1. level - Current L1 - alarm reset"
::= { notifications 16779382 }

tCurrentL1L2Activated	NOTIFICATION-TYPE
	OBJECTS	{tControllerName, tSerNum, tTrapText}
	STATUS	current
	DESCRIPTION	"Protection 2. level - Current L1 - alarm activated"
::= { notifications 150997108 }

tCurrentL1L2Disappeared	NOTIFICATION-TYPE
	OBJECTS	{tControllerName, tSerNum, tTrapText}
	STATUS	current
	DESCRIPTION	"Protection 2. level - Current L1 - alarm disappeared"
::= { notifications 150997109 }

tCurrentL1L2AlarmReset	NOTIFICATION-TYPE
	OBJECTS	{tControllerName, tSerNum, tTrapText}
	STATUS	current
	DESCRIPTION	"Protection 2. level - Current L1 - alarm reset"
::= { notifications 150997110 }

tCurrentL1SFActivated	NOTIFICATION-TYPE
	OBJECTS	{tControllerName, tSerNum, tTrapText}
	STATUS	current
	DESCRIPTION	"Protection Sensor Fail - Current L1 - alarm activated"
::= { notifications 285214836 }

tCurrentL1SFDisappeared	NOTIFICATION-TYPE
	OBJECTS	{tControllerName, tSerNum, tTrapText}
	STATUS	current
	DESCRIPTION	"Protection Sensor Fail - Current L1 - alarm disappeared"
::= { notifications 285214837 }

tCurrentL1SFAlarmReset	NOTIFICATION-TYPE
	OBJECTS	{tControllerName, tSerNum, tTrapText}
	STATUS	current
	DESCRIPTION	"Protection Sensor Fail - Current L1 - alarm reset"
::= { notifications 285214838 }

tCurrentL2L1Activated	NOTIFICATION-TYPE
	OBJECTS	{tControllerName, tSerNum, tTrapText}
	STATUS	current
	DESCRIPTION	"Protection 1. level - Current L2 - alarm activated"
::= { notifications 16779384 }

tCurrentL2L1Disappeared	NOTIFICATION-TYPE
	OBJECTS	{tControllerName, tSerNum, tTrapText}
	STATUS	current
	DESCRIPTION	"Protection 1. level - Current L2 - alarm disappeared"
::= { notifications 16779385 }

tCurrentL2L1AlarmReset	NOTIFICATION-TYPE
	OBJECTS	{tControllerName, tSerNum, tTrapText}
	STATUS	current
	DESCRIPTION	"Protection 1. level - Current L2 - alarm reset"
::= { notifications 16779386 }

tCurrentL2L2Activated	NOTIFICATION-TYPE
	OBJECTS	{tControllerName, tSerNum, tTrapText}
	STATUS	current
	DESCRIPTION	"Protection 2. level - Current L2 - alarm activated"
::= { notifications 150997112 }

tCurrentL2L2Disappeared	NOTIFICATION-TYPE
	OBJECTS	{tControllerName, tSerNum, tTrapText}
	STATUS	current
	DESCRIPTION	"Protection 2. level - Current L2 - alarm disappeared"
::= { notifications 150997113 }

tCurrentL2L2AlarmReset	NOTIFICATION-TYPE
	OBJECTS	{tControllerName, tSerNum, tTrapText}
	STATUS	current
	DESCRIPTION	"Protection 2. level - Current L2 - alarm reset"
::= { notifications 150997114 }

tCurrentL2SFActivated	NOTIFICATION-TYPE
	OBJECTS	{tControllerName, tSerNum, tTrapText}
	STATUS	current
	DESCRIPTION	"Protection Sensor Fail - Current L2 - alarm activated"
::= { notifications 285214840 }

tCurrentL2SFDisappeared	NOTIFICATION-TYPE
	OBJECTS	{tControllerName, tSerNum, tTrapText}
	STATUS	current
	DESCRIPTION	"Protection Sensor Fail - Current L2 - alarm disappeared"
::= { notifications 285214841 }

tCurrentL2SFAlarmReset	NOTIFICATION-TYPE
	OBJECTS	{tControllerName, tSerNum, tTrapText}
	STATUS	current
	DESCRIPTION	"Protection Sensor Fail - Current L2 - alarm reset"
::= { notifications 285214842 }

tCurrentL3L1Activated	NOTIFICATION-TYPE
	OBJECTS	{tControllerName, tSerNum, tTrapText}
	STATUS	current
	DESCRIPTION	"Protection 1. level - Current L3 - alarm activated"
::= { notifications 16779388 }

tCurrentL3L1Disappeared	NOTIFICATION-TYPE
	OBJECTS	{tControllerName, tSerNum, tTrapText}
	STATUS	current
	DESCRIPTION	"Protection 1. level - Current L3 - alarm disappeared"
::= { notifications 16779389 }

tCurrentL3L1AlarmReset	NOTIFICATION-TYPE
	OBJECTS	{tControllerName, tSerNum, tTrapText}
	STATUS	current
	DESCRIPTION	"Protection 1. level - Current L3 - alarm reset"
::= { notifications 16779390 }

tCurrentL3L2Activated	NOTIFICATION-TYPE
	OBJECTS	{tControllerName, tSerNum, tTrapText}
	STATUS	current
	DESCRIPTION	"Protection 2. level - Current L3 - alarm activated"
::= { notifications 150997116 }

tCurrentL3L2Disappeared	NOTIFICATION-TYPE
	OBJECTS	{tControllerName, tSerNum, tTrapText}
	STATUS	current
	DESCRIPTION	"Protection 2. level - Current L3 - alarm disappeared"
::= { notifications 150997117 }

tCurrentL3L2AlarmReset	NOTIFICATION-TYPE
	OBJECTS	{tControllerName, tSerNum, tTrapText}
	STATUS	current
	DESCRIPTION	"Protection 2. level - Current L3 - alarm reset"
::= { notifications 150997118 }

tCurrentL3SFActivated	NOTIFICATION-TYPE
	OBJECTS	{tControllerName, tSerNum, tTrapText}
	STATUS	current
	DESCRIPTION	"Protection Sensor Fail - Current L3 - alarm activated"
::= { notifications 285214844 }

tCurrentL3SFDisappeared	NOTIFICATION-TYPE
	OBJECTS	{tControllerName, tSerNum, tTrapText}
	STATUS	current
	DESCRIPTION	"Protection Sensor Fail - Current L3 - alarm disappeared"
::= { notifications 285214845 }

tCurrentL3SFAlarmReset	NOTIFICATION-TYPE
	OBJECTS	{tControllerName, tSerNum, tTrapText}
	STATUS	current
	DESCRIPTION	"Protection Sensor Fail - Current L3 - alarm reset"
::= { notifications 285214846 }

tActivePowerL1Activated3	NOTIFICATION-TYPE
	OBJECTS	{tControllerName, tSerNum, tTrapText}
	STATUS	current
	DESCRIPTION	"Protection 1. level - Active Power - alarm activated"
::= { notifications 16779396 }

tActivePowerL1Disappeared3	NOTIFICATION-TYPE
	OBJECTS	{tControllerName, tSerNum, tTrapText}
	STATUS	current
	DESCRIPTION	"Protection 1. level - Active Power - alarm disappeared"
::= { notifications 16779397 }

tActivePowerL1AlarmReset3	NOTIFICATION-TYPE
	OBJECTS	{tControllerName, tSerNum, tTrapText}
	STATUS	current
	DESCRIPTION	"Protection 1. level - Active Power - alarm reset"
::= { notifications 16779398 }

tActivePowerL2Activated3	NOTIFICATION-TYPE
	OBJECTS	{tControllerName, tSerNum, tTrapText}
	STATUS	current
	DESCRIPTION	"Protection 2. level - Active Power - alarm activated"
::= { notifications 150997124 }

tActivePowerL2Disappeared3	NOTIFICATION-TYPE
	OBJECTS	{tControllerName, tSerNum, tTrapText}
	STATUS	current
	DESCRIPTION	"Protection 2. level - Active Power - alarm disappeared"
::= { notifications 150997125 }

tActivePowerL2AlarmReset3	NOTIFICATION-TYPE
	OBJECTS	{tControllerName, tSerNum, tTrapText}
	STATUS	current
	DESCRIPTION	"Protection 2. level - Active Power - alarm reset"
::= { notifications 150997126 }

tActivePowerSFActivated3	NOTIFICATION-TYPE
	OBJECTS	{tControllerName, tSerNum, tTrapText}
	STATUS	current
	DESCRIPTION	"Protection Sensor Fail - Active Power - alarm activated"
::= { notifications 285214852 }

tActivePowerSFDisappeared3	NOTIFICATION-TYPE
	OBJECTS	{tControllerName, tSerNum, tTrapText}
	STATUS	current
	DESCRIPTION	"Protection Sensor Fail - Active Power - alarm disappeared"
::= { notifications 285214853 }

tActivePowerSFAlarmReset3	NOTIFICATION-TYPE
	OBJECTS	{tControllerName, tSerNum, tTrapText}
	STATUS	current
	DESCRIPTION	"Protection Sensor Fail - Active Power - alarm reset"
::= { notifications 285214854 }

tGridVoltageL1L2L1Activated	NOTIFICATION-TYPE
	OBJECTS	{tControllerName, tSerNum, tTrapText}
	STATUS	current
	DESCRIPTION	"Protection 1. level - Grid Voltage L1L2 - alarm activated"
::= { notifications 16779400 }

tGridVoltageL1L2L1Disappeared	NOTIFICATION-TYPE
	OBJECTS	{tControllerName, tSerNum, tTrapText}
	STATUS	current
	DESCRIPTION	"Protection 1. level - Grid Voltage L1L2 - alarm disappeared"
::= { notifications 16779401 }

tGridVoltageL1L2L1AlarmReset	NOTIFICATION-TYPE
	OBJECTS	{tControllerName, tSerNum, tTrapText}
	STATUS	current
	DESCRIPTION	"Protection 1. level - Grid Voltage L1L2 - alarm reset"
::= { notifications 16779402 }

tGridVoltageL1L2L2Activated	NOTIFICATION-TYPE
	OBJECTS	{tControllerName, tSerNum, tTrapText}
	STATUS	current
	DESCRIPTION	"Protection 2. level - Grid Voltage L1L2 - alarm activated"
::= { notifications 150997128 }

tGridVoltageL1L2L2Disappeared	NOTIFICATION-TYPE
	OBJECTS	{tControllerName, tSerNum, tTrapText}
	STATUS	current
	DESCRIPTION	"Protection 2. level - Grid Voltage L1L2 - alarm disappeared"
::= { notifications 150997129 }

tGridVoltageL1L2L2AlarmReset	NOTIFICATION-TYPE
	OBJECTS	{tControllerName, tSerNum, tTrapText}
	STATUS	current
	DESCRIPTION	"Protection 2. level - Grid Voltage L1L2 - alarm reset"
::= { notifications 150997130 }

tGridVoltageL1L2SFActivated	NOTIFICATION-TYPE
	OBJECTS	{tControllerName, tSerNum, tTrapText}
	STATUS	current
	DESCRIPTION	"Protection Sensor Fail - Grid Voltage L1L2 - alarm activated"
::= { notifications 285214856 }

tGridVoltageL1L2SFDisappeared	NOTIFICATION-TYPE
	OBJECTS	{tControllerName, tSerNum, tTrapText}
	STATUS	current
	DESCRIPTION	"Protection Sensor Fail - Grid Voltage L1L2 - alarm disappeared"
::= { notifications 285214857 }

tGridVoltageL1L2SFAlarmReset	NOTIFICATION-TYPE
	OBJECTS	{tControllerName, tSerNum, tTrapText}
	STATUS	current
	DESCRIPTION	"Protection Sensor Fail - Grid Voltage L1L2 - alarm reset"
::= { notifications 285214858 }

tGridVoltageL2L3L1Activated	NOTIFICATION-TYPE
	OBJECTS	{tControllerName, tSerNum, tTrapText}
	STATUS	current
	DESCRIPTION	"Protection 1. level - Grid Voltage L2L3 - alarm activated"
::= { notifications 16779404 }

tGridVoltageL2L3L1Disappeared	NOTIFICATION-TYPE
	OBJECTS	{tControllerName, tSerNum, tTrapText}
	STATUS	current
	DESCRIPTION	"Protection 1. level - Grid Voltage L2L3 - alarm disappeared"
::= { notifications 16779405 }

tGridVoltageL2L3L1AlarmReset	NOTIFICATION-TYPE
	OBJECTS	{tControllerName, tSerNum, tTrapText}
	STATUS	current
	DESCRIPTION	"Protection 1. level - Grid Voltage L2L3 - alarm reset"
::= { notifications 16779406 }

tGridVoltageL2L3L2Activated	NOTIFICATION-TYPE
	OBJECTS	{tControllerName, tSerNum, tTrapText}
	STATUS	current
	DESCRIPTION	"Protection 2. level - Grid Voltage L2L3 - alarm activated"
::= { notifications 150997132 }

tGridVoltageL2L3L2Disappeared	NOTIFICATION-TYPE
	OBJECTS	{tControllerName, tSerNum, tTrapText}
	STATUS	current
	DESCRIPTION	"Protection 2. level - Grid Voltage L2L3 - alarm disappeared"
::= { notifications 150997133 }

tGridVoltageL2L3L2AlarmReset	NOTIFICATION-TYPE
	OBJECTS	{tControllerName, tSerNum, tTrapText}
	STATUS	current
	DESCRIPTION	"Protection 2. level - Grid Voltage L2L3 - alarm reset"
::= { notifications 150997134 }

tGridVoltageL2L3SFActivated	NOTIFICATION-TYPE
	OBJECTS	{tControllerName, tSerNum, tTrapText}
	STATUS	current
	DESCRIPTION	"Protection Sensor Fail - Grid Voltage L2L3 - alarm activated"
::= { notifications 285214860 }

tGridVoltageL2L3SFDisappeared	NOTIFICATION-TYPE
	OBJECTS	{tControllerName, tSerNum, tTrapText}
	STATUS	current
	DESCRIPTION	"Protection Sensor Fail - Grid Voltage L2L3 - alarm disappeared"
::= { notifications 285214861 }

tGridVoltageL2L3SFAlarmReset	NOTIFICATION-TYPE
	OBJECTS	{tControllerName, tSerNum, tTrapText}
	STATUS	current
	DESCRIPTION	"Protection Sensor Fail - Grid Voltage L2L3 - alarm reset"
::= { notifications 285214862 }

tGridVoltageL3L1L1Activated	NOTIFICATION-TYPE
	OBJECTS	{tControllerName, tSerNum, tTrapText}
	STATUS	current
	DESCRIPTION	"Protection 1. level - Grid Voltage L3L1 - alarm activated"
::= { notifications 16779408 }

tGridVoltageL3L1L1Disappeared	NOTIFICATION-TYPE
	OBJECTS	{tControllerName, tSerNum, tTrapText}
	STATUS	current
	DESCRIPTION	"Protection 1. level - Grid Voltage L3L1 - alarm disappeared"
::= { notifications 16779409 }

tGridVoltageL3L1L1AlarmReset	NOTIFICATION-TYPE
	OBJECTS	{tControllerName, tSerNum, tTrapText}
	STATUS	current
	DESCRIPTION	"Protection 1. level - Grid Voltage L3L1 - alarm reset"
::= { notifications 16779410 }

tGridVoltageL3L1L2Activated	NOTIFICATION-TYPE
	OBJECTS	{tControllerName, tSerNum, tTrapText}
	STATUS	current
	DESCRIPTION	"Protection 2. level - Grid Voltage L3L1 - alarm activated"
::= { notifications 150997136 }

tGridVoltageL3L1L2Disappeared	NOTIFICATION-TYPE
	OBJECTS	{tControllerName, tSerNum, tTrapText}
	STATUS	current
	DESCRIPTION	"Protection 2. level - Grid Voltage L3L1 - alarm disappeared"
::= { notifications 150997137 }

tGridVoltageL3L1L2AlarmReset	NOTIFICATION-TYPE
	OBJECTS	{tControllerName, tSerNum, tTrapText}
	STATUS	current
	DESCRIPTION	"Protection 2. level - Grid Voltage L3L1 - alarm reset"
::= { notifications 150997138 }

tGridVoltageL3L1SFActivated	NOTIFICATION-TYPE
	OBJECTS	{tControllerName, tSerNum, tTrapText}
	STATUS	current
	DESCRIPTION	"Protection Sensor Fail - Grid Voltage L3L1 - alarm activated"
::= { notifications 285214864 }

tGridVoltageL3L1SFDisappeared	NOTIFICATION-TYPE
	OBJECTS	{tControllerName, tSerNum, tTrapText}
	STATUS	current
	DESCRIPTION	"Protection Sensor Fail - Grid Voltage L3L1 - alarm disappeared"
::= { notifications 285214865 }

tGridVoltageL3L1SFAlarmReset	NOTIFICATION-TYPE
	OBJECTS	{tControllerName, tSerNum, tTrapText}
	STATUS	current
	DESCRIPTION	"Protection Sensor Fail - Grid Voltage L3L1 - alarm reset"
::= { notifications 285214866 }

tGridFrequencyL1Activated	NOTIFICATION-TYPE
	OBJECTS	{tControllerName, tSerNum, tTrapText}
	STATUS	current
	DESCRIPTION	"Protection 1. level - Grid Frequency - alarm activated"
::= { notifications 16779412 }

tGridFrequencyL1Disappeared	NOTIFICATION-TYPE
	OBJECTS	{tControllerName, tSerNum, tTrapText}
	STATUS	current
	DESCRIPTION	"Protection 1. level - Grid Frequency - alarm disappeared"
::= { notifications 16779413 }

tGridFrequencyL1AlarmReset	NOTIFICATION-TYPE
	OBJECTS	{tControllerName, tSerNum, tTrapText}
	STATUS	current
	DESCRIPTION	"Protection 1. level - Grid Frequency - alarm reset"
::= { notifications 16779414 }

tGridFrequencyL2Activated	NOTIFICATION-TYPE
	OBJECTS	{tControllerName, tSerNum, tTrapText}
	STATUS	current
	DESCRIPTION	"Protection 2. level - Grid Frequency - alarm activated"
::= { notifications 150997140 }

tGridFrequencyL2Disappeared	NOTIFICATION-TYPE
	OBJECTS	{tControllerName, tSerNum, tTrapText}
	STATUS	current
	DESCRIPTION	"Protection 2. level - Grid Frequency - alarm disappeared"
::= { notifications 150997141 }

tGridFrequencyL2AlarmReset	NOTIFICATION-TYPE
	OBJECTS	{tControllerName, tSerNum, tTrapText}
	STATUS	current
	DESCRIPTION	"Protection 2. level - Grid Frequency - alarm reset"
::= { notifications 150997142 }

tGridFrequencySFActivated	NOTIFICATION-TYPE
	OBJECTS	{tControllerName, tSerNum, tTrapText}
	STATUS	current
	DESCRIPTION	"Protection Sensor Fail - Grid Frequency - alarm activated"
::= { notifications 285214868 }

tGridFrequencySFDisappeared	NOTIFICATION-TYPE
	OBJECTS	{tControllerName, tSerNum, tTrapText}
	STATUS	current
	DESCRIPTION	"Protection Sensor Fail - Grid Frequency - alarm disappeared"
::= { notifications 285214869 }

tGridFrequencySFAlarmReset	NOTIFICATION-TYPE
	OBJECTS	{tControllerName, tSerNum, tTrapText}
	STATUS	current
	DESCRIPTION	"Protection Sensor Fail - Grid Frequency - alarm reset"
::= { notifications 285214870 }

tReactivePowerL1Activated3	NOTIFICATION-TYPE
	OBJECTS	{tControllerName, tSerNum, tTrapText}
	STATUS	current
	DESCRIPTION	"Protection 1. level - Reactive Power - alarm activated"
::= { notifications 16779420 }

tReactivePowerL1Disappeared3	NOTIFICATION-TYPE
	OBJECTS	{tControllerName, tSerNum, tTrapText}
	STATUS	current
	DESCRIPTION	"Protection 1. level - Reactive Power - alarm disappeared"
::= { notifications 16779421 }

tReactivePowerL1AlarmReset3	NOTIFICATION-TYPE
	OBJECTS	{tControllerName, tSerNum, tTrapText}
	STATUS	current
	DESCRIPTION	"Protection 1. level - Reactive Power - alarm reset"
::= { notifications 16779422 }

tReactivePowerL2Activated3	NOTIFICATION-TYPE
	OBJECTS	{tControllerName, tSerNum, tTrapText}
	STATUS	current
	DESCRIPTION	"Protection 2. level - Reactive Power - alarm activated"
::= { notifications 150997148 }

tReactivePowerL2Disappeared3	NOTIFICATION-TYPE
	OBJECTS	{tControllerName, tSerNum, tTrapText}
	STATUS	current
	DESCRIPTION	"Protection 2. level - Reactive Power - alarm disappeared"
::= { notifications 150997149 }

tReactivePowerL2AlarmReset3	NOTIFICATION-TYPE
	OBJECTS	{tControllerName, tSerNum, tTrapText}
	STATUS	current
	DESCRIPTION	"Protection 2. level - Reactive Power - alarm reset"
::= { notifications 150997150 }

tReactivePowerSFActivated3	NOTIFICATION-TYPE
	OBJECTS	{tControllerName, tSerNum, tTrapText}
	STATUS	current
	DESCRIPTION	"Protection Sensor Fail - Reactive Power - alarm activated"
::= { notifications 285214876 }

tReactivePowerSFDisappeared3	NOTIFICATION-TYPE
	OBJECTS	{tControllerName, tSerNum, tTrapText}
	STATUS	current
	DESCRIPTION	"Protection Sensor Fail - Reactive Power - alarm disappeared"
::= { notifications 285214877 }

tReactivePowerSFAlarmReset3	NOTIFICATION-TYPE
	OBJECTS	{tControllerName, tSerNum, tTrapText}
	STATUS	current
	DESCRIPTION	"Protection Sensor Fail - Reactive Power - alarm reset"
::= { notifications 285214878 }

tEmergencyStopL2Activated	NOTIFICATION-TYPE
	OBJECTS	{tControllerName, tSerNum, tTrapText}
	STATUS	current
	DESCRIPTION	"Protection 2. level - Emergency Stop - alarm activated"
::= { notifications 159383728 }

tEmergencyStopL2Disappeared	NOTIFICATION-TYPE
	OBJECTS	{tControllerName, tSerNum, tTrapText}
	STATUS	current
	DESCRIPTION	"Protection 2. level - Emergency Stop - alarm disappeared"
::= { notifications 159383729 }

tEmergencyStopL2AlarmReset	NOTIFICATION-TYPE
	OBJECTS	{tControllerName, tSerNum, tTrapText}
	STATUS	current
	DESCRIPTION	"Protection 2. level - Emergency Stop - alarm reset"
::= { notifications 159383730 }

tBESSVoltageL1NL1Activated	NOTIFICATION-TYPE
	OBJECTS	{tControllerName, tSerNum, tTrapText}
	STATUS	current
	DESCRIPTION	"Protection 1. level - BESS Voltage L1-N - alarm activated"
::= { notifications 25166276 }

tBESSVoltageL1NL1Disappeared	NOTIFICATION-TYPE
	OBJECTS	{tControllerName, tSerNum, tTrapText}
	STATUS	current
	DESCRIPTION	"Protection 1. level - BESS Voltage L1-N - alarm disappeared"
::= { notifications 25166277 }

tBESSVoltageL1NL1AlarmReset	NOTIFICATION-TYPE
	OBJECTS	{tControllerName, tSerNum, tTrapText}
	STATUS	current
	DESCRIPTION	"Protection 1. level - BESS Voltage L1-N - alarm reset"
::= { notifications 25166278 }

tBESSVoltageL1NL2Activated	NOTIFICATION-TYPE
	OBJECTS	{tControllerName, tSerNum, tTrapText}
	STATUS	current
	DESCRIPTION	"Protection 2. level - BESS Voltage L1-N - alarm activated"
::= { notifications 159384004 }

tBESSVoltageL1NL2Disappeared	NOTIFICATION-TYPE
	OBJECTS	{tControllerName, tSerNum, tTrapText}
	STATUS	current
	DESCRIPTION	"Protection 2. level - BESS Voltage L1-N - alarm disappeared"
::= { notifications 159384005 }

tBESSVoltageL1NL2AlarmReset	NOTIFICATION-TYPE
	OBJECTS	{tControllerName, tSerNum, tTrapText}
	STATUS	current
	DESCRIPTION	"Protection 2. level - BESS Voltage L1-N - alarm reset"
::= { notifications 159384006 }

tBESSVoltageL1NSFActivated	NOTIFICATION-TYPE
	OBJECTS	{tControllerName, tSerNum, tTrapText}
	STATUS	current
	DESCRIPTION	"Protection Sensor Fail - BESS Voltage L1-N - alarm activated"
::= { notifications 293601732 }

tBESSVoltageL1NSFDisappeared	NOTIFICATION-TYPE
	OBJECTS	{tControllerName, tSerNum, tTrapText}
	STATUS	current
	DESCRIPTION	"Protection Sensor Fail - BESS Voltage L1-N - alarm disappeared"
::= { notifications 293601733 }

tBESSVoltageL1NSFAlarmReset	NOTIFICATION-TYPE
	OBJECTS	{tControllerName, tSerNum, tTrapText}
	STATUS	current
	DESCRIPTION	"Protection Sensor Fail - BESS Voltage L1-N - alarm reset"
::= { notifications 293601734 }

tBESSVoltageL2NL1Activated	NOTIFICATION-TYPE
	OBJECTS	{tControllerName, tSerNum, tTrapText}
	STATUS	current
	DESCRIPTION	"Protection 1. level - BESS Voltage L2-N - alarm activated"
::= { notifications 25166280 }

tBESSVoltageL2NL1Disappeared	NOTIFICATION-TYPE
	OBJECTS	{tControllerName, tSerNum, tTrapText}
	STATUS	current
	DESCRIPTION	"Protection 1. level - BESS Voltage L2-N - alarm disappeared"
::= { notifications 25166281 }

tBESSVoltageL2NL1AlarmReset	NOTIFICATION-TYPE
	OBJECTS	{tControllerName, tSerNum, tTrapText}
	STATUS	current
	DESCRIPTION	"Protection 1. level - BESS Voltage L2-N - alarm reset"
::= { notifications 25166282 }

tBESSVoltageL2NL2Activated	NOTIFICATION-TYPE
	OBJECTS	{tControllerName, tSerNum, tTrapText}
	STATUS	current
	DESCRIPTION	"Protection 2. level - BESS Voltage L2-N - alarm activated"
::= { notifications 159384008 }

tBESSVoltageL2NL2Disappeared	NOTIFICATION-TYPE
	OBJECTS	{tControllerName, tSerNum, tTrapText}
	STATUS	current
	DESCRIPTION	"Protection 2. level - BESS Voltage L2-N - alarm disappeared"
::= { notifications 159384009 }

tBESSVoltageL2NL2AlarmReset	NOTIFICATION-TYPE
	OBJECTS	{tControllerName, tSerNum, tTrapText}
	STATUS	current
	DESCRIPTION	"Protection 2. level - BESS Voltage L2-N - alarm reset"
::= { notifications 159384010 }

tBESSVoltageL2NSFActivated	NOTIFICATION-TYPE
	OBJECTS	{tControllerName, tSerNum, tTrapText}
	STATUS	current
	DESCRIPTION	"Protection Sensor Fail - BESS Voltage L2-N - alarm activated"
::= { notifications 293601736 }

tBESSVoltageL2NSFDisappeared	NOTIFICATION-TYPE
	OBJECTS	{tControllerName, tSerNum, tTrapText}
	STATUS	current
	DESCRIPTION	"Protection Sensor Fail - BESS Voltage L2-N - alarm disappeared"
::= { notifications 293601737 }

tBESSVoltageL2NSFAlarmReset	NOTIFICATION-TYPE
	OBJECTS	{tControllerName, tSerNum, tTrapText}
	STATUS	current
	DESCRIPTION	"Protection Sensor Fail - BESS Voltage L2-N - alarm reset"
::= { notifications 293601738 }

tBESSVoltageL3NL1Activated	NOTIFICATION-TYPE
	OBJECTS	{tControllerName, tSerNum, tTrapText}
	STATUS	current
	DESCRIPTION	"Protection 1. level - BESS Voltage L3-N - alarm activated"
::= { notifications 25166284 }

tBESSVoltageL3NL1Disappeared	NOTIFICATION-TYPE
	OBJECTS	{tControllerName, tSerNum, tTrapText}
	STATUS	current
	DESCRIPTION	"Protection 1. level - BESS Voltage L3-N - alarm disappeared"
::= { notifications 25166285 }

tBESSVoltageL3NL1AlarmReset	NOTIFICATION-TYPE
	OBJECTS	{tControllerName, tSerNum, tTrapText}
	STATUS	current
	DESCRIPTION	"Protection 1. level - BESS Voltage L3-N - alarm reset"
::= { notifications 25166286 }

tBESSVoltageL3NL2Activated	NOTIFICATION-TYPE
	OBJECTS	{tControllerName, tSerNum, tTrapText}
	STATUS	current
	DESCRIPTION	"Protection 2. level - BESS Voltage L3-N - alarm activated"
::= { notifications 159384012 }

tBESSVoltageL3NL2Disappeared	NOTIFICATION-TYPE
	OBJECTS	{tControllerName, tSerNum, tTrapText}
	STATUS	current
	DESCRIPTION	"Protection 2. level - BESS Voltage L3-N - alarm disappeared"
::= { notifications 159384013 }

tBESSVoltageL3NL2AlarmReset	NOTIFICATION-TYPE
	OBJECTS	{tControllerName, tSerNum, tTrapText}
	STATUS	current
	DESCRIPTION	"Protection 2. level - BESS Voltage L3-N - alarm reset"
::= { notifications 159384014 }

tBESSVoltageL3NSFActivated	NOTIFICATION-TYPE
	OBJECTS	{tControllerName, tSerNum, tTrapText}
	STATUS	current
	DESCRIPTION	"Protection Sensor Fail - BESS Voltage L3-N - alarm activated"
::= { notifications 293601740 }

tBESSVoltageL3NSFDisappeared	NOTIFICATION-TYPE
	OBJECTS	{tControllerName, tSerNum, tTrapText}
	STATUS	current
	DESCRIPTION	"Protection Sensor Fail - BESS Voltage L3-N - alarm disappeared"
::= { notifications 293601741 }

tBESSVoltageL3NSFAlarmReset	NOTIFICATION-TYPE
	OBJECTS	{tControllerName, tSerNum, tTrapText}
	STATUS	current
	DESCRIPTION	"Protection Sensor Fail - BESS Voltage L3-N - alarm reset"
::= { notifications 293601742 }

tBESSVoltageL1L2L1Activated	NOTIFICATION-TYPE
	OBJECTS	{tControllerName, tSerNum, tTrapText}
	STATUS	current
	DESCRIPTION	"Protection 1. level - BESS Voltage L1-L2 - alarm activated"
::= { notifications 25166288 }

tBESSVoltageL1L2L1Disappeared	NOTIFICATION-TYPE
	OBJECTS	{tControllerName, tSerNum, tTrapText}
	STATUS	current
	DESCRIPTION	"Protection 1. level - BESS Voltage L1-L2 - alarm disappeared"
::= { notifications 25166289 }

tBESSVoltageL1L2L1AlarmReset	NOTIFICATION-TYPE
	OBJECTS	{tControllerName, tSerNum, tTrapText}
	STATUS	current
	DESCRIPTION	"Protection 1. level - BESS Voltage L1-L2 - alarm reset"
::= { notifications 25166290 }

tBESSVoltageL1L2L2Activated	NOTIFICATION-TYPE
	OBJECTS	{tControllerName, tSerNum, tTrapText}
	STATUS	current
	DESCRIPTION	"Protection 2. level - BESS Voltage L1-L2 - alarm activated"
::= { notifications 159384016 }

tBESSVoltageL1L2L2Disappeared	NOTIFICATION-TYPE
	OBJECTS	{tControllerName, tSerNum, tTrapText}
	STATUS	current
	DESCRIPTION	"Protection 2. level - BESS Voltage L1-L2 - alarm disappeared"
::= { notifications 159384017 }

tBESSVoltageL1L2L2AlarmReset	NOTIFICATION-TYPE
	OBJECTS	{tControllerName, tSerNum, tTrapText}
	STATUS	current
	DESCRIPTION	"Protection 2. level - BESS Voltage L1-L2 - alarm reset"
::= { notifications 159384018 }

tBESSVoltageL1L2SFActivated	NOTIFICATION-TYPE
	OBJECTS	{tControllerName, tSerNum, tTrapText}
	STATUS	current
	DESCRIPTION	"Protection Sensor Fail - BESS Voltage L1-L2 - alarm activated"
::= { notifications 293601744 }

tBESSVoltageL1L2SFDisappeared	NOTIFICATION-TYPE
	OBJECTS	{tControllerName, tSerNum, tTrapText}
	STATUS	current
	DESCRIPTION	"Protection Sensor Fail - BESS Voltage L1-L2 - alarm disappeared"
::= { notifications 293601745 }

tBESSVoltageL1L2SFAlarmReset	NOTIFICATION-TYPE
	OBJECTS	{tControllerName, tSerNum, tTrapText}
	STATUS	current
	DESCRIPTION	"Protection Sensor Fail - BESS Voltage L1-L2 - alarm reset"
::= { notifications 293601746 }

tBESSVoltageL2L3L1Activated	NOTIFICATION-TYPE
	OBJECTS	{tControllerName, tSerNum, tTrapText}
	STATUS	current
	DESCRIPTION	"Protection 1. level - BESS Voltage L2-L3 - alarm activated"
::= { notifications 25166292 }

tBESSVoltageL2L3L1Disappeared	NOTIFICATION-TYPE
	OBJECTS	{tControllerName, tSerNum, tTrapText}
	STATUS	current
	DESCRIPTION	"Protection 1. level - BESS Voltage L2-L3 - alarm disappeared"
::= { notifications 25166293 }

tBESSVoltageL2L3L1AlarmReset	NOTIFICATION-TYPE
	OBJECTS	{tControllerName, tSerNum, tTrapText}
	STATUS	current
	DESCRIPTION	"Protection 1. level - BESS Voltage L2-L3 - alarm reset"
::= { notifications 25166294 }

tBESSVoltageL2L3L2Activated	NOTIFICATION-TYPE
	OBJECTS	{tControllerName, tSerNum, tTrapText}
	STATUS	current
	DESCRIPTION	"Protection 2. level - BESS Voltage L2-L3 - alarm activated"
::= { notifications 159384020 }

tBESSVoltageL2L3L2Disappeared	NOTIFICATION-TYPE
	OBJECTS	{tControllerName, tSerNum, tTrapText}
	STATUS	current
	DESCRIPTION	"Protection 2. level - BESS Voltage L2-L3 - alarm disappeared"
::= { notifications 159384021 }

tBESSVoltageL2L3L2AlarmReset	NOTIFICATION-TYPE
	OBJECTS	{tControllerName, tSerNum, tTrapText}
	STATUS	current
	DESCRIPTION	"Protection 2. level - BESS Voltage L2-L3 - alarm reset"
::= { notifications 159384022 }

tBESSVoltageL2L3SFActivated	NOTIFICATION-TYPE
	OBJECTS	{tControllerName, tSerNum, tTrapText}
	STATUS	current
	DESCRIPTION	"Protection Sensor Fail - BESS Voltage L2-L3 - alarm activated"
::= { notifications 293601748 }

tBESSVoltageL2L3SFDisappeared	NOTIFICATION-TYPE
	OBJECTS	{tControllerName, tSerNum, tTrapText}
	STATUS	current
	DESCRIPTION	"Protection Sensor Fail - BESS Voltage L2-L3 - alarm disappeared"
::= { notifications 293601749 }

tBESSVoltageL2L3SFAlarmReset	NOTIFICATION-TYPE
	OBJECTS	{tControllerName, tSerNum, tTrapText}
	STATUS	current
	DESCRIPTION	"Protection Sensor Fail - BESS Voltage L2-L3 - alarm reset"
::= { notifications 293601750 }

tBESSVoltageL3L1L1Activated	NOTIFICATION-TYPE
	OBJECTS	{tControllerName, tSerNum, tTrapText}
	STATUS	current
	DESCRIPTION	"Protection 1. level - BESS Voltage L3-L1 - alarm activated"
::= { notifications 25166296 }

tBESSVoltageL3L1L1Disappeared	NOTIFICATION-TYPE
	OBJECTS	{tControllerName, tSerNum, tTrapText}
	STATUS	current
	DESCRIPTION	"Protection 1. level - BESS Voltage L3-L1 - alarm disappeared"
::= { notifications 25166297 }

tBESSVoltageL3L1L1AlarmReset	NOTIFICATION-TYPE
	OBJECTS	{tControllerName, tSerNum, tTrapText}
	STATUS	current
	DESCRIPTION	"Protection 1. level - BESS Voltage L3-L1 - alarm reset"
::= { notifications 25166298 }

tBESSVoltageL3L1L2Activated	NOTIFICATION-TYPE
	OBJECTS	{tControllerName, tSerNum, tTrapText}
	STATUS	current
	DESCRIPTION	"Protection 2. level - BESS Voltage L3-L1 - alarm activated"
::= { notifications 159384024 }

tBESSVoltageL3L1L2Disappeared	NOTIFICATION-TYPE
	OBJECTS	{tControllerName, tSerNum, tTrapText}
	STATUS	current
	DESCRIPTION	"Protection 2. level - BESS Voltage L3-L1 - alarm disappeared"
::= { notifications 159384025 }

tBESSVoltageL3L1L2AlarmReset	NOTIFICATION-TYPE
	OBJECTS	{tControllerName, tSerNum, tTrapText}
	STATUS	current
	DESCRIPTION	"Protection 2. level - BESS Voltage L3-L1 - alarm reset"
::= { notifications 159384026 }

tBESSVoltageL3L1SFActivated	NOTIFICATION-TYPE
	OBJECTS	{tControllerName, tSerNum, tTrapText}
	STATUS	current
	DESCRIPTION	"Protection Sensor Fail - BESS Voltage L3-L1 - alarm activated"
::= { notifications 293601752 }

tBESSVoltageL3L1SFDisappeared	NOTIFICATION-TYPE
	OBJECTS	{tControllerName, tSerNum, tTrapText}
	STATUS	current
	DESCRIPTION	"Protection Sensor Fail - BESS Voltage L3-L1 - alarm disappeared"
::= { notifications 293601753 }

tBESSVoltageL3L1SFAlarmReset	NOTIFICATION-TYPE
	OBJECTS	{tControllerName, tSerNum, tTrapText}
	STATUS	current
	DESCRIPTION	"Protection Sensor Fail - BESS Voltage L3-L1 - alarm reset"
::= { notifications 293601754 }

tBESSFrequencyL1Activated	NOTIFICATION-TYPE
	OBJECTS	{tControllerName, tSerNum, tTrapText}
	STATUS	current
	DESCRIPTION	"Protection 1. level - BESS Frequency - alarm activated"
::= { notifications 25166300 }

tBESSFrequencyL1Disappeared	NOTIFICATION-TYPE
	OBJECTS	{tControllerName, tSerNum, tTrapText}
	STATUS	current
	DESCRIPTION	"Protection 1. level - BESS Frequency - alarm disappeared"
::= { notifications 25166301 }

tBESSFrequencyL1AlarmReset	NOTIFICATION-TYPE
	OBJECTS	{tControllerName, tSerNum, tTrapText}
	STATUS	current
	DESCRIPTION	"Protection 1. level - BESS Frequency - alarm reset"
::= { notifications 25166302 }

tBESSFrequencyL2Activated	NOTIFICATION-TYPE
	OBJECTS	{tControllerName, tSerNum, tTrapText}
	STATUS	current
	DESCRIPTION	"Protection 2. level - BESS Frequency - alarm activated"
::= { notifications 159384028 }

tBESSFrequencyL2Disappeared	NOTIFICATION-TYPE
	OBJECTS	{tControllerName, tSerNum, tTrapText}
	STATUS	current
	DESCRIPTION	"Protection 2. level - BESS Frequency - alarm disappeared"
::= { notifications 159384029 }

tBESSFrequencyL2AlarmReset	NOTIFICATION-TYPE
	OBJECTS	{tControllerName, tSerNum, tTrapText}
	STATUS	current
	DESCRIPTION	"Protection 2. level - BESS Frequency - alarm reset"
::= { notifications 159384030 }

tBESSFrequencySFActivated	NOTIFICATION-TYPE
	OBJECTS	{tControllerName, tSerNum, tTrapText}
	STATUS	current
	DESCRIPTION	"Protection Sensor Fail - BESS Frequency - alarm activated"
::= { notifications 293601756 }

tBESSFrequencySFDisappeared	NOTIFICATION-TYPE
	OBJECTS	{tControllerName, tSerNum, tTrapText}
	STATUS	current
	DESCRIPTION	"Protection Sensor Fail - BESS Frequency - alarm disappeared"
::= { notifications 293601757 }

tBESSFrequencySFAlarmReset	NOTIFICATION-TYPE
	OBJECTS	{tControllerName, tSerNum, tTrapText}
	STATUS	current
	DESCRIPTION	"Protection Sensor Fail - BESS Frequency - alarm reset"
::= { notifications 293601758 }

tMainsCHR2FBusVoltageL1NL1Activated	NOTIFICATION-TYPE
	OBJECTS	{tControllerName, tSerNum, tTrapText}
	STATUS	current
	DESCRIPTION	"Protection 1. level - Mains/Bus Voltage L1-N - alarm activated"
::= { notifications 25166368 }

tMainsCHR2FBusVoltageL1NL1Disappeared	NOTIFICATION-TYPE
	OBJECTS	{tControllerName, tSerNum, tTrapText}
	STATUS	current
	DESCRIPTION	"Protection 1. level - Mains/Bus Voltage L1-N - alarm disappeared"
::= { notifications 25166369 }

tMainsCHR2FBusVoltageL1NL1AlarmReset	NOTIFICATION-TYPE
	OBJECTS	{tControllerName, tSerNum, tTrapText}
	STATUS	current
	DESCRIPTION	"Protection 1. level - Mains/Bus Voltage L1-N - alarm reset"
::= { notifications 25166370 }

tMainsCHR2FBusVoltageL1NL2Activated	NOTIFICATION-TYPE
	OBJECTS	{tControllerName, tSerNum, tTrapText}
	STATUS	current
	DESCRIPTION	"Protection 2. level - Mains/Bus Voltage L1-N - alarm activated"
::= { notifications 159384096 }

tMainsCHR2FBusVoltageL1NL2Disappeared	NOTIFICATION-TYPE
	OBJECTS	{tControllerName, tSerNum, tTrapText}
	STATUS	current
	DESCRIPTION	"Protection 2. level - Mains/Bus Voltage L1-N - alarm disappeared"
::= { notifications 159384097 }

tMainsCHR2FBusVoltageL1NL2AlarmReset	NOTIFICATION-TYPE
	OBJECTS	{tControllerName, tSerNum, tTrapText}
	STATUS	current
	DESCRIPTION	"Protection 2. level - Mains/Bus Voltage L1-N - alarm reset"
::= { notifications 159384098 }

tMainsCHR2FBusVoltageL1NSFActivated	NOTIFICATION-TYPE
	OBJECTS	{tControllerName, tSerNum, tTrapText}
	STATUS	current
	DESCRIPTION	"Protection Sensor Fail - Mains/Bus Voltage L1-N - alarm activated"
::= { notifications 293601824 }

tMainsCHR2FBusVoltageL1NSFDisappeared	NOTIFICATION-TYPE
	OBJECTS	{tControllerName, tSerNum, tTrapText}
	STATUS	current
	DESCRIPTION	"Protection Sensor Fail - Mains/Bus Voltage L1-N - alarm disappeared"
::= { notifications 293601825 }

tMainsCHR2FBusVoltageL1NSFAlarmReset	NOTIFICATION-TYPE
	OBJECTS	{tControllerName, tSerNum, tTrapText}
	STATUS	current
	DESCRIPTION	"Protection Sensor Fail - Mains/Bus Voltage L1-N - alarm reset"
::= { notifications 293601826 }

tMainsCHR2FBusVoltageL2NL1Activated	NOTIFICATION-TYPE
	OBJECTS	{tControllerName, tSerNum, tTrapText}
	STATUS	current
	DESCRIPTION	"Protection 1. level - Mains/Bus Voltage L2-N - alarm activated"
::= { notifications 25166372 }

tMainsCHR2FBusVoltageL2NL1Disappeared	NOTIFICATION-TYPE
	OBJECTS	{tControllerName, tSerNum, tTrapText}
	STATUS	current
	DESCRIPTION	"Protection 1. level - Mains/Bus Voltage L2-N - alarm disappeared"
::= { notifications 25166373 }

tMainsCHR2FBusVoltageL2NL1AlarmReset	NOTIFICATION-TYPE
	OBJECTS	{tControllerName, tSerNum, tTrapText}
	STATUS	current
	DESCRIPTION	"Protection 1. level - Mains/Bus Voltage L2-N - alarm reset"
::= { notifications 25166374 }

tMainsCHR2FBusVoltageL2NL2Activated	NOTIFICATION-TYPE
	OBJECTS	{tControllerName, tSerNum, tTrapText}
	STATUS	current
	DESCRIPTION	"Protection 2. level - Mains/Bus Voltage L2-N - alarm activated"
::= { notifications 159384100 }

tMainsCHR2FBusVoltageL2NL2Disappeared	NOTIFICATION-TYPE
	OBJECTS	{tControllerName, tSerNum, tTrapText}
	STATUS	current
	DESCRIPTION	"Protection 2. level - Mains/Bus Voltage L2-N - alarm disappeared"
::= { notifications 159384101 }

tMainsCHR2FBusVoltageL2NL2AlarmReset	NOTIFICATION-TYPE
	OBJECTS	{tControllerName, tSerNum, tTrapText}
	STATUS	current
	DESCRIPTION	"Protection 2. level - Mains/Bus Voltage L2-N - alarm reset"
::= { notifications 159384102 }

tMainsCHR2FBusVoltageL2NSFActivated	NOTIFICATION-TYPE
	OBJECTS	{tControllerName, tSerNum, tTrapText}
	STATUS	current
	DESCRIPTION	"Protection Sensor Fail - Mains/Bus Voltage L2-N - alarm activated"
::= { notifications 293601828 }

tMainsCHR2FBusVoltageL2NSFDisappeared	NOTIFICATION-TYPE
	OBJECTS	{tControllerName, tSerNum, tTrapText}
	STATUS	current
	DESCRIPTION	"Protection Sensor Fail - Mains/Bus Voltage L2-N - alarm disappeared"
::= { notifications 293601829 }

tMainsCHR2FBusVoltageL2NSFAlarmReset	NOTIFICATION-TYPE
	OBJECTS	{tControllerName, tSerNum, tTrapText}
	STATUS	current
	DESCRIPTION	"Protection Sensor Fail - Mains/Bus Voltage L2-N - alarm reset"
::= { notifications 293601830 }

tMainsCHR2FBusVoltageL3NL1Activated	NOTIFICATION-TYPE
	OBJECTS	{tControllerName, tSerNum, tTrapText}
	STATUS	current
	DESCRIPTION	"Protection 1. level - Mains/Bus Voltage L3-N - alarm activated"
::= { notifications 25166376 }

tMainsCHR2FBusVoltageL3NL1Disappeared	NOTIFICATION-TYPE
	OBJECTS	{tControllerName, tSerNum, tTrapText}
	STATUS	current
	DESCRIPTION	"Protection 1. level - Mains/Bus Voltage L3-N - alarm disappeared"
::= { notifications 25166377 }

tMainsCHR2FBusVoltageL3NL1AlarmReset	NOTIFICATION-TYPE
	OBJECTS	{tControllerName, tSerNum, tTrapText}
	STATUS	current
	DESCRIPTION	"Protection 1. level - Mains/Bus Voltage L3-N - alarm reset"
::= { notifications 25166378 }

tMainsCHR2FBusVoltageL3NL2Activated	NOTIFICATION-TYPE
	OBJECTS	{tControllerName, tSerNum, tTrapText}
	STATUS	current
	DESCRIPTION	"Protection 2. level - Mains/Bus Voltage L3-N - alarm activated"
::= { notifications 159384104 }

tMainsCHR2FBusVoltageL3NL2Disappeared	NOTIFICATION-TYPE
	OBJECTS	{tControllerName, tSerNum, tTrapText}
	STATUS	current
	DESCRIPTION	"Protection 2. level - Mains/Bus Voltage L3-N - alarm disappeared"
::= { notifications 159384105 }

tMainsCHR2FBusVoltageL3NL2AlarmReset	NOTIFICATION-TYPE
	OBJECTS	{tControllerName, tSerNum, tTrapText}
	STATUS	current
	DESCRIPTION	"Protection 2. level - Mains/Bus Voltage L3-N - alarm reset"
::= { notifications 159384106 }

tMainsCHR2FBusVoltageL3NSFActivated	NOTIFICATION-TYPE
	OBJECTS	{tControllerName, tSerNum, tTrapText}
	STATUS	current
	DESCRIPTION	"Protection Sensor Fail - Mains/Bus Voltage L3-N - alarm activated"
::= { notifications 293601832 }

tMainsCHR2FBusVoltageL3NSFDisappeared	NOTIFICATION-TYPE
	OBJECTS	{tControllerName, tSerNum, tTrapText}
	STATUS	current
	DESCRIPTION	"Protection Sensor Fail - Mains/Bus Voltage L3-N - alarm disappeared"
::= { notifications 293601833 }

tMainsCHR2FBusVoltageL3NSFAlarmReset	NOTIFICATION-TYPE
	OBJECTS	{tControllerName, tSerNum, tTrapText}
	STATUS	current
	DESCRIPTION	"Protection Sensor Fail - Mains/Bus Voltage L3-N - alarm reset"
::= { notifications 293601834 }

tMainsCHR2FBusVoltageL1L2L1Activated	NOTIFICATION-TYPE
	OBJECTS	{tControllerName, tSerNum, tTrapText}
	STATUS	current
	DESCRIPTION	"Protection 1. level - Mains/Bus Voltage L1-L2 - alarm activated"
::= { notifications 25166380 }

tMainsCHR2FBusVoltageL1L2L1Disappeared	NOTIFICATION-TYPE
	OBJECTS	{tControllerName, tSerNum, tTrapText}
	STATUS	current
	DESCRIPTION	"Protection 1. level - Mains/Bus Voltage L1-L2 - alarm disappeared"
::= { notifications 25166381 }

tMainsCHR2FBusVoltageL1L2L1AlarmReset	NOTIFICATION-TYPE
	OBJECTS	{tControllerName, tSerNum, tTrapText}
	STATUS	current
	DESCRIPTION	"Protection 1. level - Mains/Bus Voltage L1-L2 - alarm reset"
::= { notifications 25166382 }

tMainsCHR2FBusVoltageL1L2L2Activated	NOTIFICATION-TYPE
	OBJECTS	{tControllerName, tSerNum, tTrapText}
	STATUS	current
	DESCRIPTION	"Protection 2. level - Mains/Bus Voltage L1-L2 - alarm activated"
::= { notifications 159384108 }

tMainsCHR2FBusVoltageL1L2L2Disappeared	NOTIFICATION-TYPE
	OBJECTS	{tControllerName, tSerNum, tTrapText}
	STATUS	current
	DESCRIPTION	"Protection 2. level - Mains/Bus Voltage L1-L2 - alarm disappeared"
::= { notifications 159384109 }

tMainsCHR2FBusVoltageL1L2L2AlarmReset	NOTIFICATION-TYPE
	OBJECTS	{tControllerName, tSerNum, tTrapText}
	STATUS	current
	DESCRIPTION	"Protection 2. level - Mains/Bus Voltage L1-L2 - alarm reset"
::= { notifications 159384110 }

tMainsCHR2FBusVoltageL1L2SFActivated	NOTIFICATION-TYPE
	OBJECTS	{tControllerName, tSerNum, tTrapText}
	STATUS	current
	DESCRIPTION	"Protection Sensor Fail - Mains/Bus Voltage L1-L2 - alarm activated"
::= { notifications 293601836 }

tMainsCHR2FBusVoltageL1L2SFDisappeared	NOTIFICATION-TYPE
	OBJECTS	{tControllerName, tSerNum, tTrapText}
	STATUS	current
	DESCRIPTION	"Protection Sensor Fail - Mains/Bus Voltage L1-L2 - alarm disappeared"
::= { notifications 293601837 }

tMainsCHR2FBusVoltageL1L2SFAlarmReset	NOTIFICATION-TYPE
	OBJECTS	{tControllerName, tSerNum, tTrapText}
	STATUS	current
	DESCRIPTION	"Protection Sensor Fail - Mains/Bus Voltage L1-L2 - alarm reset"
::= { notifications 293601838 }

tMainsCHR2FBusVoltageL2L3L1Activated	NOTIFICATION-TYPE
	OBJECTS	{tControllerName, tSerNum, tTrapText}
	STATUS	current
	DESCRIPTION	"Protection 1. level - Mains/Bus Voltage L2-L3 - alarm activated"
::= { notifications 25166384 }

tMainsCHR2FBusVoltageL2L3L1Disappeared	NOTIFICATION-TYPE
	OBJECTS	{tControllerName, tSerNum, tTrapText}
	STATUS	current
	DESCRIPTION	"Protection 1. level - Mains/Bus Voltage L2-L3 - alarm disappeared"
::= { notifications 25166385 }

tMainsCHR2FBusVoltageL2L3L1AlarmReset	NOTIFICATION-TYPE
	OBJECTS	{tControllerName, tSerNum, tTrapText}
	STATUS	current
	DESCRIPTION	"Protection 1. level - Mains/Bus Voltage L2-L3 - alarm reset"
::= { notifications 25166386 }

tMainsCHR2FBusVoltageL2L3L2Activated	NOTIFICATION-TYPE
	OBJECTS	{tControllerName, tSerNum, tTrapText}
	STATUS	current
	DESCRIPTION	"Protection 2. level - Mains/Bus Voltage L2-L3 - alarm activated"
::= { notifications 159384112 }

tMainsCHR2FBusVoltageL2L3L2Disappeared	NOTIFICATION-TYPE
	OBJECTS	{tControllerName, tSerNum, tTrapText}
	STATUS	current
	DESCRIPTION	"Protection 2. level - Mains/Bus Voltage L2-L3 - alarm disappeared"
::= { notifications 159384113 }

tMainsCHR2FBusVoltageL2L3L2AlarmReset	NOTIFICATION-TYPE
	OBJECTS	{tControllerName, tSerNum, tTrapText}
	STATUS	current
	DESCRIPTION	"Protection 2. level - Mains/Bus Voltage L2-L3 - alarm reset"
::= { notifications 159384114 }

tMainsCHR2FBusVoltageL2L3SFActivated	NOTIFICATION-TYPE
	OBJECTS	{tControllerName, tSerNum, tTrapText}
	STATUS	current
	DESCRIPTION	"Protection Sensor Fail - Mains/Bus Voltage L2-L3 - alarm activated"
::= { notifications 293601840 }

tMainsCHR2FBusVoltageL2L3SFDisappeared	NOTIFICATION-TYPE
	OBJECTS	{tControllerName, tSerNum, tTrapText}
	STATUS	current
	DESCRIPTION	"Protection Sensor Fail - Mains/Bus Voltage L2-L3 - alarm disappeared"
::= { notifications 293601841 }

tMainsCHR2FBusVoltageL2L3SFAlarmReset	NOTIFICATION-TYPE
	OBJECTS	{tControllerName, tSerNum, tTrapText}
	STATUS	current
	DESCRIPTION	"Protection Sensor Fail - Mains/Bus Voltage L2-L3 - alarm reset"
::= { notifications 293601842 }

tMainsCHR2FBusVoltageL3L1L1Activated	NOTIFICATION-TYPE
	OBJECTS	{tControllerName, tSerNum, tTrapText}
	STATUS	current
	DESCRIPTION	"Protection 1. level - Mains/Bus Voltage L3-L1 - alarm activated"
::= { notifications 25166388 }

tMainsCHR2FBusVoltageL3L1L1Disappeared	NOTIFICATION-TYPE
	OBJECTS	{tControllerName, tSerNum, tTrapText}
	STATUS	current
	DESCRIPTION	"Protection 1. level - Mains/Bus Voltage L3-L1 - alarm disappeared"
::= { notifications 25166389 }

tMainsCHR2FBusVoltageL3L1L1AlarmReset	NOTIFICATION-TYPE
	OBJECTS	{tControllerName, tSerNum, tTrapText}
	STATUS	current
	DESCRIPTION	"Protection 1. level - Mains/Bus Voltage L3-L1 - alarm reset"
::= { notifications 25166390 }

tMainsCHR2FBusVoltageL3L1L2Activated	NOTIFICATION-TYPE
	OBJECTS	{tControllerName, tSerNum, tTrapText}
	STATUS	current
	DESCRIPTION	"Protection 2. level - Mains/Bus Voltage L3-L1 - alarm activated"
::= { notifications 159384116 }

tMainsCHR2FBusVoltageL3L1L2Disappeared	NOTIFICATION-TYPE
	OBJECTS	{tControllerName, tSerNum, tTrapText}
	STATUS	current
	DESCRIPTION	"Protection 2. level - Mains/Bus Voltage L3-L1 - alarm disappeared"
::= { notifications 159384117 }

tMainsCHR2FBusVoltageL3L1L2AlarmReset	NOTIFICATION-TYPE
	OBJECTS	{tControllerName, tSerNum, tTrapText}
	STATUS	current
	DESCRIPTION	"Protection 2. level - Mains/Bus Voltage L3-L1 - alarm reset"
::= { notifications 159384118 }

tMainsCHR2FBusVoltageL3L1SFActivated	NOTIFICATION-TYPE
	OBJECTS	{tControllerName, tSerNum, tTrapText}
	STATUS	current
	DESCRIPTION	"Protection Sensor Fail - Mains/Bus Voltage L3-L1 - alarm activated"
::= { notifications 293601844 }

tMainsCHR2FBusVoltageL3L1SFDisappeared	NOTIFICATION-TYPE
	OBJECTS	{tControllerName, tSerNum, tTrapText}
	STATUS	current
	DESCRIPTION	"Protection Sensor Fail - Mains/Bus Voltage L3-L1 - alarm disappeared"
::= { notifications 293601845 }

tMainsCHR2FBusVoltageL3L1SFAlarmReset	NOTIFICATION-TYPE
	OBJECTS	{tControllerName, tSerNum, tTrapText}
	STATUS	current
	DESCRIPTION	"Protection Sensor Fail - Mains/Bus Voltage L3-L1 - alarm reset"
::= { notifications 293601846 }

tMainsCHR2FBusFrequencyL1Activated	NOTIFICATION-TYPE
	OBJECTS	{tControllerName, tSerNum, tTrapText}
	STATUS	current
	DESCRIPTION	"Protection 1. level - Mains/Bus Frequency - alarm activated"
::= { notifications 25166392 }

tMainsCHR2FBusFrequencyL1Disappeared	NOTIFICATION-TYPE
	OBJECTS	{tControllerName, tSerNum, tTrapText}
	STATUS	current
	DESCRIPTION	"Protection 1. level - Mains/Bus Frequency - alarm disappeared"
::= { notifications 25166393 }

tMainsCHR2FBusFrequencyL1AlarmReset	NOTIFICATION-TYPE
	OBJECTS	{tControllerName, tSerNum, tTrapText}
	STATUS	current
	DESCRIPTION	"Protection 1. level - Mains/Bus Frequency - alarm reset"
::= { notifications 25166394 }

tMainsCHR2FBusFrequencyL2Activated	NOTIFICATION-TYPE
	OBJECTS	{tControllerName, tSerNum, tTrapText}
	STATUS	current
	DESCRIPTION	"Protection 2. level - Mains/Bus Frequency - alarm activated"
::= { notifications 159384120 }

tMainsCHR2FBusFrequencyL2Disappeared	NOTIFICATION-TYPE
	OBJECTS	{tControllerName, tSerNum, tTrapText}
	STATUS	current
	DESCRIPTION	"Protection 2. level - Mains/Bus Frequency - alarm disappeared"
::= { notifications 159384121 }

tMainsCHR2FBusFrequencyL2AlarmReset	NOTIFICATION-TYPE
	OBJECTS	{tControllerName, tSerNum, tTrapText}
	STATUS	current
	DESCRIPTION	"Protection 2. level - Mains/Bus Frequency - alarm reset"
::= { notifications 159384122 }

tMainsCHR2FBusFrequencySFActivated	NOTIFICATION-TYPE
	OBJECTS	{tControllerName, tSerNum, tTrapText}
	STATUS	current
	DESCRIPTION	"Protection Sensor Fail - Mains/Bus Frequency - alarm activated"
::= { notifications 293601848 }

tMainsCHR2FBusFrequencySFDisappeared	NOTIFICATION-TYPE
	OBJECTS	{tControllerName, tSerNum, tTrapText}
	STATUS	current
	DESCRIPTION	"Protection Sensor Fail - Mains/Bus Frequency - alarm disappeared"
::= { notifications 293601849 }

tMainsCHR2FBusFrequencySFAlarmReset	NOTIFICATION-TYPE
	OBJECTS	{tControllerName, tSerNum, tTrapText}
	STATUS	current
	DESCRIPTION	"Protection Sensor Fail - Mains/Bus Frequency - alarm reset"
::= { notifications 293601850 }

tMainsCHR2FBusVUnbalancePhNL1Activated	NOTIFICATION-TYPE
	OBJECTS	{tControllerName, tSerNum, tTrapText}
	STATUS	current
	DESCRIPTION	"Protection 1. level - Mains/Bus V Unbalance Ph-N - alarm activated"
::= { notifications 25172288 }

tMainsCHR2FBusVUnbalancePhNL1Disappeared	NOTIFICATION-TYPE
	OBJECTS	{tControllerName, tSerNum, tTrapText}
	STATUS	current
	DESCRIPTION	"Protection 1. level - Mains/Bus V Unbalance Ph-N - alarm disappeared"
::= { notifications 25172289 }

tMainsCHR2FBusVUnbalancePhNL1AlarmReset	NOTIFICATION-TYPE
	OBJECTS	{tControllerName, tSerNum, tTrapText}
	STATUS	current
	DESCRIPTION	"Protection 1. level - Mains/Bus V Unbalance Ph-N - alarm reset"
::= { notifications 25172290 }

tMainsCHR2FBusVUnbalancePhNL2Activated1	NOTIFICATION-TYPE
	OBJECTS	{tControllerName, tSerNum, tTrapText}
	STATUS	current
	DESCRIPTION	"Protection 2. level - Mains/Bus V Unbalance Ph-N - alarm activated"
::= { notifications 159390016 }

tMainsCHR2FBusVUnbalancePhNL2Disappeared1	NOTIFICATION-TYPE
	OBJECTS	{tControllerName, tSerNum, tTrapText}
	STATUS	current
	DESCRIPTION	"Protection 2. level - Mains/Bus V Unbalance Ph-N - alarm disappeared"
::= { notifications 159390017 }

tMainsCHR2FBusVUnbalancePhNL2AlarmReset1	NOTIFICATION-TYPE
	OBJECTS	{tControllerName, tSerNum, tTrapText}
	STATUS	current
	DESCRIPTION	"Protection 2. level - Mains/Bus V Unbalance Ph-N - alarm reset"
::= { notifications 159390018 }

tMainsCHR2FBusVUnbalancePhNSFActivated	NOTIFICATION-TYPE
	OBJECTS	{tControllerName, tSerNum, tTrapText}
	STATUS	current
	DESCRIPTION	"Protection Sensor Fail - Mains/Bus V Unbalance Ph-N - alarm activated"
::= { notifications 293607744 }

tMainsCHR2FBusVUnbalancePhNSFDisappeared	NOTIFICATION-TYPE
	OBJECTS	{tControllerName, tSerNum, tTrapText}
	STATUS	current
	DESCRIPTION	"Protection Sensor Fail - Mains/Bus V Unbalance Ph-N - alarm disappeared"
::= { notifications 293607745 }

tMainsCHR2FBusVUnbalancePhNSFAlarmReset	NOTIFICATION-TYPE
	OBJECTS	{tControllerName, tSerNum, tTrapText}
	STATUS	current
	DESCRIPTION	"Protection Sensor Fail - Mains/Bus V Unbalance Ph-N - alarm reset"
::= { notifications 293607746 }

tMainsCHR2FBusVUnbalancePhPhL1Activated	NOTIFICATION-TYPE
	OBJECTS	{tControllerName, tSerNum, tTrapText}
	STATUS	current
	DESCRIPTION	"Protection 1. level - Mains/Bus V Unbalance Ph-Ph - alarm activated"
::= { notifications 25172292 }

tMainsCHR2FBusVUnbalancePhPhL1Disappeared	NOTIFICATION-TYPE
	OBJECTS	{tControllerName, tSerNum, tTrapText}
	STATUS	current
	DESCRIPTION	"Protection 1. level - Mains/Bus V Unbalance Ph-Ph - alarm disappeared"
::= { notifications 25172293 }

tMainsCHR2FBusVUnbalancePhPhL1AlarmReset	NOTIFICATION-TYPE
	OBJECTS	{tControllerName, tSerNum, tTrapText}
	STATUS	current
	DESCRIPTION	"Protection 1. level - Mains/Bus V Unbalance Ph-Ph - alarm reset"
::= { notifications 25172294 }

tMainsCHR2FBusVUnbalancePhPhL2Activated1	NOTIFICATION-TYPE
	OBJECTS	{tControllerName, tSerNum, tTrapText}
	STATUS	current
	DESCRIPTION	"Protection 2. level - Mains/Bus V Unbalance Ph-Ph - alarm activated"
::= { notifications 159390020 }

tMainsCHR2FBusVUnbalancePhPhL2Disappeared1	NOTIFICATION-TYPE
	OBJECTS	{tControllerName, tSerNum, tTrapText}
	STATUS	current
	DESCRIPTION	"Protection 2. level - Mains/Bus V Unbalance Ph-Ph - alarm disappeared"
::= { notifications 159390021 }

tMainsCHR2FBusVUnbalancePhPhL2AlarmReset1	NOTIFICATION-TYPE
	OBJECTS	{tControllerName, tSerNum, tTrapText}
	STATUS	current
	DESCRIPTION	"Protection 2. level - Mains/Bus V Unbalance Ph-Ph - alarm reset"
::= { notifications 159390022 }

tMainsCHR2FBusVUnbalancePhPhSFActivated	NOTIFICATION-TYPE
	OBJECTS	{tControllerName, tSerNum, tTrapText}
	STATUS	current
	DESCRIPTION	"Protection Sensor Fail - Mains/Bus V Unbalance Ph-Ph - alarm activated"
::= { notifications 293607748 }

tMainsCHR2FBusVUnbalancePhPhSFDisappeared	NOTIFICATION-TYPE
	OBJECTS	{tControllerName, tSerNum, tTrapText}
	STATUS	current
	DESCRIPTION	"Protection Sensor Fail - Mains/Bus V Unbalance Ph-Ph - alarm disappeared"
::= { notifications 293607749 }

tMainsCHR2FBusVUnbalancePhPhSFAlarmReset	NOTIFICATION-TYPE
	OBJECTS	{tControllerName, tSerNum, tTrapText}
	STATUS	current
	DESCRIPTION	"Protection Sensor Fail - Mains/Bus V Unbalance Ph-Ph - alarm reset"
::= { notifications 293607750 }

tBESSVUnbalancePhPhL1Activated	NOTIFICATION-TYPE
	OBJECTS	{tControllerName, tSerNum, tTrapText}
	STATUS	current
	DESCRIPTION	"Protection 1. level - BESS V Unbalance Ph-Ph - alarm activated"
::= { notifications 25172272 }

tBESSVUnbalancePhPhL1Disappeared	NOTIFICATION-TYPE
	OBJECTS	{tControllerName, tSerNum, tTrapText}
	STATUS	current
	DESCRIPTION	"Protection 1. level - BESS V Unbalance Ph-Ph - alarm disappeared"
::= { notifications 25172273 }

tBESSVUnbalancePhPhL1AlarmReset	NOTIFICATION-TYPE
	OBJECTS	{tControllerName, tSerNum, tTrapText}
	STATUS	current
	DESCRIPTION	"Protection 1. level - BESS V Unbalance Ph-Ph - alarm reset"
::= { notifications 25172274 }

tBESSVUnbalancePhPhL2Activated1	NOTIFICATION-TYPE
	OBJECTS	{tControllerName, tSerNum, tTrapText}
	STATUS	current
	DESCRIPTION	"Protection 2. level - BESS V Unbalance Ph-Ph - alarm activated"
::= { notifications 159390000 }

tBESSVUnbalancePhPhL2Disappeared1	NOTIFICATION-TYPE
	OBJECTS	{tControllerName, tSerNum, tTrapText}
	STATUS	current
	DESCRIPTION	"Protection 2. level - BESS V Unbalance Ph-Ph - alarm disappeared"
::= { notifications 159390001 }

tBESSVUnbalancePhPhL2AlarmReset1	NOTIFICATION-TYPE
	OBJECTS	{tControllerName, tSerNum, tTrapText}
	STATUS	current
	DESCRIPTION	"Protection 2. level - BESS V Unbalance Ph-Ph - alarm reset"
::= { notifications 159390002 }

tBESSVUnbalancePhPhSFActivated	NOTIFICATION-TYPE
	OBJECTS	{tControllerName, tSerNum, tTrapText}
	STATUS	current
	DESCRIPTION	"Protection Sensor Fail - BESS V Unbalance Ph-Ph - alarm activated"
::= { notifications 293607728 }

tBESSVUnbalancePhPhSFDisappeared	NOTIFICATION-TYPE
	OBJECTS	{tControllerName, tSerNum, tTrapText}
	STATUS	current
	DESCRIPTION	"Protection Sensor Fail - BESS V Unbalance Ph-Ph - alarm disappeared"
::= { notifications 293607729 }

tBESSVUnbalancePhPhSFAlarmReset	NOTIFICATION-TYPE
	OBJECTS	{tControllerName, tSerNum, tTrapText}
	STATUS	current
	DESCRIPTION	"Protection Sensor Fail - BESS V Unbalance Ph-Ph - alarm reset"
::= { notifications 293607730 }

tBESSVUnbalancePhNL1Activated	NOTIFICATION-TYPE
	OBJECTS	{tControllerName, tSerNum, tTrapText}
	STATUS	current
	DESCRIPTION	"Protection 1. level - BESS V Unbalance Ph-N - alarm activated"
::= { notifications 25172276 }

tBESSVUnbalancePhNL1Disappeared	NOTIFICATION-TYPE
	OBJECTS	{tControllerName, tSerNum, tTrapText}
	STATUS	current
	DESCRIPTION	"Protection 1. level - BESS V Unbalance Ph-N - alarm disappeared"
::= { notifications 25172277 }

tBESSVUnbalancePhNL1AlarmReset	NOTIFICATION-TYPE
	OBJECTS	{tControllerName, tSerNum, tTrapText}
	STATUS	current
	DESCRIPTION	"Protection 1. level - BESS V Unbalance Ph-N - alarm reset"
::= { notifications 25172278 }

tBESSVUnbalancePhNL2Activated1	NOTIFICATION-TYPE
	OBJECTS	{tControllerName, tSerNum, tTrapText}
	STATUS	current
	DESCRIPTION	"Protection 2. level - BESS V Unbalance Ph-N - alarm activated"
::= { notifications 159390004 }

tBESSVUnbalancePhNL2Disappeared1	NOTIFICATION-TYPE
	OBJECTS	{tControllerName, tSerNum, tTrapText}
	STATUS	current
	DESCRIPTION	"Protection 2. level - BESS V Unbalance Ph-N - alarm disappeared"
::= { notifications 159390005 }

tBESSVUnbalancePhNL2AlarmReset1	NOTIFICATION-TYPE
	OBJECTS	{tControllerName, tSerNum, tTrapText}
	STATUS	current
	DESCRIPTION	"Protection 2. level - BESS V Unbalance Ph-N - alarm reset"
::= { notifications 159390006 }

tBESSVUnbalancePhNSFActivated	NOTIFICATION-TYPE
	OBJECTS	{tControllerName, tSerNum, tTrapText}
	STATUS	current
	DESCRIPTION	"Protection Sensor Fail - BESS V Unbalance Ph-N - alarm activated"
::= { notifications 293607732 }

tBESSVUnbalancePhNSFDisappeared	NOTIFICATION-TYPE
	OBJECTS	{tControllerName, tSerNum, tTrapText}
	STATUS	current
	DESCRIPTION	"Protection Sensor Fail - BESS V Unbalance Ph-N - alarm disappeared"
::= { notifications 293607733 }

tBESSVUnbalancePhNSFAlarmReset	NOTIFICATION-TYPE
	OBJECTS	{tControllerName, tSerNum, tTrapText}
	STATUS	current
	DESCRIPTION	"Protection Sensor Fail - BESS V Unbalance Ph-N - alarm reset"
::= { notifications 293607734 }

tBESSCurrentUnbalanceL1Activated	NOTIFICATION-TYPE
	OBJECTS	{tControllerName, tSerNum, tTrapText}
	STATUS	current
	DESCRIPTION	"Protection 1. level - BESS Current Unbalance - alarm activated"
::= { notifications 25172284 }

tBESSCurrentUnbalanceL1Disappeared	NOTIFICATION-TYPE
	OBJECTS	{tControllerName, tSerNum, tTrapText}
	STATUS	current
	DESCRIPTION	"Protection 1. level - BESS Current Unbalance - alarm disappeared"
::= { notifications 25172285 }

tBESSCurrentUnbalanceL1AlarmReset	NOTIFICATION-TYPE
	OBJECTS	{tControllerName, tSerNum, tTrapText}
	STATUS	current
	DESCRIPTION	"Protection 1. level - BESS Current Unbalance - alarm reset"
::= { notifications 25172286 }

tBESSCurrentUnbalanceL2Activated1	NOTIFICATION-TYPE
	OBJECTS	{tControllerName, tSerNum, tTrapText}
	STATUS	current
	DESCRIPTION	"Protection 2. level - BESS Current Unbalance - alarm activated"
::= { notifications 159390012 }

tBESSCurrentUnbalanceL2Disappeared1	NOTIFICATION-TYPE
	OBJECTS	{tControllerName, tSerNum, tTrapText}
	STATUS	current
	DESCRIPTION	"Protection 2. level - BESS Current Unbalance - alarm disappeared"
::= { notifications 159390013 }

tBESSCurrentUnbalanceL2AlarmReset1	NOTIFICATION-TYPE
	OBJECTS	{tControllerName, tSerNum, tTrapText}
	STATUS	current
	DESCRIPTION	"Protection 2. level - BESS Current Unbalance - alarm reset"
::= { notifications 159390014 }

tBESSCurrentUnbalanceSFActivated	NOTIFICATION-TYPE
	OBJECTS	{tControllerName, tSerNum, tTrapText}
	STATUS	current
	DESCRIPTION	"Protection Sensor Fail - BESS Current Unbalance - alarm activated"
::= { notifications 293607740 }

tBESSCurrentUnbalanceSFDisappeared	NOTIFICATION-TYPE
	OBJECTS	{tControllerName, tSerNum, tTrapText}
	STATUS	current
	DESCRIPTION	"Protection Sensor Fail - BESS Current Unbalance - alarm disappeared"
::= { notifications 293607741 }

tBESSCurrentUnbalanceSFAlarmReset	NOTIFICATION-TYPE
	OBJECTS	{tControllerName, tSerNum, tTrapText}
	STATUS	current
	DESCRIPTION	"Protection Sensor Fail - BESS Current Unbalance - alarm reset"
::= { notifications 293607742 }

tMainsCHR2FBusGtVL1NL2Activated	NOTIFICATION-TYPE
	OBJECTS	{tControllerName, tSerNum, tTrapText}
	STATUS	current
	DESCRIPTION	"Protection 2. level - Mains/Bus >V L1-N - alarm activated"
::= { notifications 159384052 }

tMainsCHR2FBusGtVL1NL2Disappeared	NOTIFICATION-TYPE
	OBJECTS	{tControllerName, tSerNum, tTrapText}
	STATUS	current
	DESCRIPTION	"Protection 2. level - Mains/Bus >V L1-N - alarm disappeared"
::= { notifications 159384053 }

tMainsCHR2FBusGtVL1NL2AlarmReset	NOTIFICATION-TYPE
	OBJECTS	{tControllerName, tSerNum, tTrapText}
	STATUS	current
	DESCRIPTION	"Protection 2. level - Mains/Bus >V L1-N - alarm reset"
::= { notifications 159384054 }

tMainsCHR2FBusLtVL1NL2Activated	NOTIFICATION-TYPE
	OBJECTS	{tControllerName, tSerNum, tTrapText}
	STATUS	current
	DESCRIPTION	"Protection 2. level - Mains/Bus <V L1-N - alarm activated"
::= { notifications 159384040 }

tMainsCHR2FBusLtVL1NL2Disappeared	NOTIFICATION-TYPE
	OBJECTS	{tControllerName, tSerNum, tTrapText}
	STATUS	current
	DESCRIPTION	"Protection 2. level - Mains/Bus <V L1-N - alarm disappeared"
::= { notifications 159384041 }

tMainsCHR2FBusLtVL1NL2AlarmReset	NOTIFICATION-TYPE
	OBJECTS	{tControllerName, tSerNum, tTrapText}
	STATUS	current
	DESCRIPTION	"Protection 2. level - Mains/Bus <V L1-N - alarm reset"
::= { notifications 159384042 }

tMainsCHR2FBusGtVL2NL2Activated	NOTIFICATION-TYPE
	OBJECTS	{tControllerName, tSerNum, tTrapText}
	STATUS	current
	DESCRIPTION	"Protection 2. level - Mains/Bus >V L2-N - alarm activated"
::= { notifications 159384056 }

tMainsCHR2FBusGtVL2NL2Disappeared	NOTIFICATION-TYPE
	OBJECTS	{tControllerName, tSerNum, tTrapText}
	STATUS	current
	DESCRIPTION	"Protection 2. level - Mains/Bus >V L2-N - alarm disappeared"
::= { notifications 159384057 }

tMainsCHR2FBusGtVL2NL2AlarmReset	NOTIFICATION-TYPE
	OBJECTS	{tControllerName, tSerNum, tTrapText}
	STATUS	current
	DESCRIPTION	"Protection 2. level - Mains/Bus >V L2-N - alarm reset"
::= { notifications 159384058 }

tMainsCHR2FBusLtVL2NL2Activated	NOTIFICATION-TYPE
	OBJECTS	{tControllerName, tSerNum, tTrapText}
	STATUS	current
	DESCRIPTION	"Protection 2. level - Mains/Bus <V L2-N - alarm activated"
::= { notifications 159384044 }

tMainsCHR2FBusLtVL2NL2Disappeared	NOTIFICATION-TYPE
	OBJECTS	{tControllerName, tSerNum, tTrapText}
	STATUS	current
	DESCRIPTION	"Protection 2. level - Mains/Bus <V L2-N - alarm disappeared"
::= { notifications 159384045 }

tMainsCHR2FBusLtVL2NL2AlarmReset	NOTIFICATION-TYPE
	OBJECTS	{tControllerName, tSerNum, tTrapText}
	STATUS	current
	DESCRIPTION	"Protection 2. level - Mains/Bus <V L2-N - alarm reset"
::= { notifications 159384046 }

tMainsCHR2FBusGtVL3NL2Activated	NOTIFICATION-TYPE
	OBJECTS	{tControllerName, tSerNum, tTrapText}
	STATUS	current
	DESCRIPTION	"Protection 2. level - Mains/Bus >V L3-N - alarm activated"
::= { notifications 159384060 }

tMainsCHR2FBusGtVL3NL2Disappeared	NOTIFICATION-TYPE
	OBJECTS	{tControllerName, tSerNum, tTrapText}
	STATUS	current
	DESCRIPTION	"Protection 2. level - Mains/Bus >V L3-N - alarm disappeared"
::= { notifications 159384061 }

tMainsCHR2FBusGtVL3NL2AlarmReset	NOTIFICATION-TYPE
	OBJECTS	{tControllerName, tSerNum, tTrapText}
	STATUS	current
	DESCRIPTION	"Protection 2. level - Mains/Bus >V L3-N - alarm reset"
::= { notifications 159384062 }

tMainsCHR2FBusLtVL3NL2Activated	NOTIFICATION-TYPE
	OBJECTS	{tControllerName, tSerNum, tTrapText}
	STATUS	current
	DESCRIPTION	"Protection 2. level - Mains/Bus <V L3-N - alarm activated"
::= { notifications 159384048 }

tMainsCHR2FBusLtVL3NL2Disappeared	NOTIFICATION-TYPE
	OBJECTS	{tControllerName, tSerNum, tTrapText}
	STATUS	current
	DESCRIPTION	"Protection 2. level - Mains/Bus <V L3-N - alarm disappeared"
::= { notifications 159384049 }

tMainsCHR2FBusLtVL3NL2AlarmReset	NOTIFICATION-TYPE
	OBJECTS	{tControllerName, tSerNum, tTrapText}
	STATUS	current
	DESCRIPTION	"Protection 2. level - Mains/Bus <V L3-N - alarm reset"
::= { notifications 159384050 }

tMainsCHR2FBusGtVL1L2L2Activated	NOTIFICATION-TYPE
	OBJECTS	{tControllerName, tSerNum, tTrapText}
	STATUS	current
	DESCRIPTION	"Protection 2. level - Mains/Bus >V L1-L2 - alarm activated"
::= { notifications 159384076 }

tMainsCHR2FBusGtVL1L2L2Disappeared	NOTIFICATION-TYPE
	OBJECTS	{tControllerName, tSerNum, tTrapText}
	STATUS	current
	DESCRIPTION	"Protection 2. level - Mains/Bus >V L1-L2 - alarm disappeared"
::= { notifications 159384077 }

tMainsCHR2FBusGtVL1L2L2AlarmReset	NOTIFICATION-TYPE
	OBJECTS	{tControllerName, tSerNum, tTrapText}
	STATUS	current
	DESCRIPTION	"Protection 2. level - Mains/Bus >V L1-L2 - alarm reset"
::= { notifications 159384078 }

tMainsCHR2FBusLtVL1L2L2Activated	NOTIFICATION-TYPE
	OBJECTS	{tControllerName, tSerNum, tTrapText}
	STATUS	current
	DESCRIPTION	"Protection 2. level - Mains/Bus <V L1-L2 - alarm activated"
::= { notifications 159384064 }

tMainsCHR2FBusLtVL1L2L2Disappeared	NOTIFICATION-TYPE
	OBJECTS	{tControllerName, tSerNum, tTrapText}
	STATUS	current
	DESCRIPTION	"Protection 2. level - Mains/Bus <V L1-L2 - alarm disappeared"
::= { notifications 159384065 }

tMainsCHR2FBusLtVL1L2L2AlarmReset	NOTIFICATION-TYPE
	OBJECTS	{tControllerName, tSerNum, tTrapText}
	STATUS	current
	DESCRIPTION	"Protection 2. level - Mains/Bus <V L1-L2 - alarm reset"
::= { notifications 159384066 }

tMainsCHR2FBusGtVL2L3L2Activated	NOTIFICATION-TYPE
	OBJECTS	{tControllerName, tSerNum, tTrapText}
	STATUS	current
	DESCRIPTION	"Protection 2. level - Mains/Bus >V L2-L3 - alarm activated"
::= { notifications 159384080 }

tMainsCHR2FBusGtVL2L3L2Disappeared	NOTIFICATION-TYPE
	OBJECTS	{tControllerName, tSerNum, tTrapText}
	STATUS	current
	DESCRIPTION	"Protection 2. level - Mains/Bus >V L2-L3 - alarm disappeared"
::= { notifications 159384081 }

tMainsCHR2FBusGtVL2L3L2AlarmReset	NOTIFICATION-TYPE
	OBJECTS	{tControllerName, tSerNum, tTrapText}
	STATUS	current
	DESCRIPTION	"Protection 2. level - Mains/Bus >V L2-L3 - alarm reset"
::= { notifications 159384082 }

tMainsCHR2FBusLtVL2L3L2Activated	NOTIFICATION-TYPE
	OBJECTS	{tControllerName, tSerNum, tTrapText}
	STATUS	current
	DESCRIPTION	"Protection 2. level - Mains/Bus <V L2-L3 - alarm activated"
::= { notifications 159384068 }

tMainsCHR2FBusLtVL2L3L2Disappeared	NOTIFICATION-TYPE
	OBJECTS	{tControllerName, tSerNum, tTrapText}
	STATUS	current
	DESCRIPTION	"Protection 2. level - Mains/Bus <V L2-L3 - alarm disappeared"
::= { notifications 159384069 }

tMainsCHR2FBusLtVL2L3L2AlarmReset	NOTIFICATION-TYPE
	OBJECTS	{tControllerName, tSerNum, tTrapText}
	STATUS	current
	DESCRIPTION	"Protection 2. level - Mains/Bus <V L2-L3 - alarm reset"
::= { notifications 159384070 }

tMainsCHR2FBusGtVL3L1L2Activated	NOTIFICATION-TYPE
	OBJECTS	{tControllerName, tSerNum, tTrapText}
	STATUS	current
	DESCRIPTION	"Protection 2. level - Mains/Bus >V L3-L1 - alarm activated"
::= { notifications 159384084 }

tMainsCHR2FBusGtVL3L1L2Disappeared	NOTIFICATION-TYPE
	OBJECTS	{tControllerName, tSerNum, tTrapText}
	STATUS	current
	DESCRIPTION	"Protection 2. level - Mains/Bus >V L3-L1 - alarm disappeared"
::= { notifications 159384085 }

tMainsCHR2FBusGtVL3L1L2AlarmReset	NOTIFICATION-TYPE
	OBJECTS	{tControllerName, tSerNum, tTrapText}
	STATUS	current
	DESCRIPTION	"Protection 2. level - Mains/Bus >V L3-L1 - alarm reset"
::= { notifications 159384086 }

tMainsCHR2FBusLtVL3L1L2Activated	NOTIFICATION-TYPE
	OBJECTS	{tControllerName, tSerNum, tTrapText}
	STATUS	current
	DESCRIPTION	"Protection 2. level - Mains/Bus <V L3-L1 - alarm activated"
::= { notifications 159384072 }

tMainsCHR2FBusLtVL3L1L2Disappeared	NOTIFICATION-TYPE
	OBJECTS	{tControllerName, tSerNum, tTrapText}
	STATUS	current
	DESCRIPTION	"Protection 2. level - Mains/Bus <V L3-L1 - alarm disappeared"
::= { notifications 159384073 }

tMainsCHR2FBusLtVL3L1L2AlarmReset	NOTIFICATION-TYPE
	OBJECTS	{tControllerName, tSerNum, tTrapText}
	STATUS	current
	DESCRIPTION	"Protection 2. level - Mains/Bus <V L3-L1 - alarm reset"
::= { notifications 159384074 }

tMainsCHR2FBusGtGtVL1NL2Activated	NOTIFICATION-TYPE
	OBJECTS	{tControllerName, tSerNum, tTrapText}
	STATUS	current
	DESCRIPTION	"Protection 2. level - Mains/Bus >>V L1-N - alarm activated"
::= { notifications 159387872 }

tMainsCHR2FBusGtGtVL1NL2Disappeared	NOTIFICATION-TYPE
	OBJECTS	{tControllerName, tSerNum, tTrapText}
	STATUS	current
	DESCRIPTION	"Protection 2. level - Mains/Bus >>V L1-N - alarm disappeared"
::= { notifications 159387873 }

tMainsCHR2FBusGtGtVL1NL2AlarmReset	NOTIFICATION-TYPE
	OBJECTS	{tControllerName, tSerNum, tTrapText}
	STATUS	current
	DESCRIPTION	"Protection 2. level - Mains/Bus >>V L1-N - alarm reset"
::= { notifications 159387874 }

tMainsCHR2FBusLtLtVL1NL2Activated	NOTIFICATION-TYPE
	OBJECTS	{tControllerName, tSerNum, tTrapText}
	STATUS	current
	DESCRIPTION	"Protection 2. level - Mains/Bus <<V L1-N - alarm activated"
::= { notifications 159387876 }

tMainsCHR2FBusLtLtVL1NL2Disappeared	NOTIFICATION-TYPE
	OBJECTS	{tControllerName, tSerNum, tTrapText}
	STATUS	current
	DESCRIPTION	"Protection 2. level - Mains/Bus <<V L1-N - alarm disappeared"
::= { notifications 159387877 }

tMainsCHR2FBusLtLtVL1NL2AlarmReset	NOTIFICATION-TYPE
	OBJECTS	{tControllerName, tSerNum, tTrapText}
	STATUS	current
	DESCRIPTION	"Protection 2. level - Mains/Bus <<V L1-N - alarm reset"
::= { notifications 159387878 }

tMainsCHR2FBusGtGtVL2NL2Activated	NOTIFICATION-TYPE
	OBJECTS	{tControllerName, tSerNum, tTrapText}
	STATUS	current
	DESCRIPTION	"Protection 2. level - Mains/Bus >>V L2-N - alarm activated"
::= { notifications 159387880 }

tMainsCHR2FBusGtGtVL2NL2Disappeared	NOTIFICATION-TYPE
	OBJECTS	{tControllerName, tSerNum, tTrapText}
	STATUS	current
	DESCRIPTION	"Protection 2. level - Mains/Bus >>V L2-N - alarm disappeared"
::= { notifications 159387881 }

tMainsCHR2FBusGtGtVL2NL2AlarmReset	NOTIFICATION-TYPE
	OBJECTS	{tControllerName, tSerNum, tTrapText}
	STATUS	current
	DESCRIPTION	"Protection 2. level - Mains/Bus >>V L2-N - alarm reset"
::= { notifications 159387882 }

tMainsCHR2FBusLtLtVL2NL2Activated	NOTIFICATION-TYPE
	OBJECTS	{tControllerName, tSerNum, tTrapText}
	STATUS	current
	DESCRIPTION	"Protection 2. level - Mains/Bus <<V L2-N - alarm activated"
::= { notifications 159387884 }

tMainsCHR2FBusLtLtVL2NL2Disappeared	NOTIFICATION-TYPE
	OBJECTS	{tControllerName, tSerNum, tTrapText}
	STATUS	current
	DESCRIPTION	"Protection 2. level - Mains/Bus <<V L2-N - alarm disappeared"
::= { notifications 159387885 }

tMainsCHR2FBusLtLtVL2NL2AlarmReset	NOTIFICATION-TYPE
	OBJECTS	{tControllerName, tSerNum, tTrapText}
	STATUS	current
	DESCRIPTION	"Protection 2. level - Mains/Bus <<V L2-N - alarm reset"
::= { notifications 159387886 }

tMainsCHR2FBusGtGtVL3NL2Activated	NOTIFICATION-TYPE
	OBJECTS	{tControllerName, tSerNum, tTrapText}
	STATUS	current
	DESCRIPTION	"Protection 2. level - Mains/Bus >>V L3-N - alarm activated"
::= { notifications 159387888 }

tMainsCHR2FBusGtGtVL3NL2Disappeared	NOTIFICATION-TYPE
	OBJECTS	{tControllerName, tSerNum, tTrapText}
	STATUS	current
	DESCRIPTION	"Protection 2. level - Mains/Bus >>V L3-N - alarm disappeared"
::= { notifications 159387889 }

tMainsCHR2FBusGtGtVL3NL2AlarmReset	NOTIFICATION-TYPE
	OBJECTS	{tControllerName, tSerNum, tTrapText}
	STATUS	current
	DESCRIPTION	"Protection 2. level - Mains/Bus >>V L3-N - alarm reset"
::= { notifications 159387890 }

tMainsCHR2FBusLtLtVL3NL2Activated	NOTIFICATION-TYPE
	OBJECTS	{tControllerName, tSerNum, tTrapText}
	STATUS	current
	DESCRIPTION	"Protection 2. level - Mains/Bus <<V L3-N - alarm activated"
::= { notifications 159387892 }

tMainsCHR2FBusLtLtVL3NL2Disappeared	NOTIFICATION-TYPE
	OBJECTS	{tControllerName, tSerNum, tTrapText}
	STATUS	current
	DESCRIPTION	"Protection 2. level - Mains/Bus <<V L3-N - alarm disappeared"
::= { notifications 159387893 }

tMainsCHR2FBusLtLtVL3NL2AlarmReset	NOTIFICATION-TYPE
	OBJECTS	{tControllerName, tSerNum, tTrapText}
	STATUS	current
	DESCRIPTION	"Protection 2. level - Mains/Bus <<V L3-N - alarm reset"
::= { notifications 159387894 }

tMainsCHR2FBusGtGtVL1L2L2Activated	NOTIFICATION-TYPE
	OBJECTS	{tControllerName, tSerNum, tTrapText}
	STATUS	current
	DESCRIPTION	"Protection 2. level - Mains/Bus >>V L1-L2 - alarm activated"
::= { notifications 159387896 }

tMainsCHR2FBusGtGtVL1L2L2Disappeared	NOTIFICATION-TYPE
	OBJECTS	{tControllerName, tSerNum, tTrapText}
	STATUS	current
	DESCRIPTION	"Protection 2. level - Mains/Bus >>V L1-L2 - alarm disappeared"
::= { notifications 159387897 }

tMainsCHR2FBusGtGtVL1L2L2AlarmReset	NOTIFICATION-TYPE
	OBJECTS	{tControllerName, tSerNum, tTrapText}
	STATUS	current
	DESCRIPTION	"Protection 2. level - Mains/Bus >>V L1-L2 - alarm reset"
::= { notifications 159387898 }

tMainsCHR2FBusLtLtVL1L2L2Activated	NOTIFICATION-TYPE
	OBJECTS	{tControllerName, tSerNum, tTrapText}
	STATUS	current
	DESCRIPTION	"Protection 2. level - Mains/Bus <<V L1-L2 - alarm activated"
::= { notifications 159387900 }

tMainsCHR2FBusLtLtVL1L2L2Disappeared	NOTIFICATION-TYPE
	OBJECTS	{tControllerName, tSerNum, tTrapText}
	STATUS	current
	DESCRIPTION	"Protection 2. level - Mains/Bus <<V L1-L2 - alarm disappeared"
::= { notifications 159387901 }

tMainsCHR2FBusLtLtVL1L2L2AlarmReset	NOTIFICATION-TYPE
	OBJECTS	{tControllerName, tSerNum, tTrapText}
	STATUS	current
	DESCRIPTION	"Protection 2. level - Mains/Bus <<V L1-L2 - alarm reset"
::= { notifications 159387902 }

tMainsCHR2FBusGtGtVL2L3L2Activated	NOTIFICATION-TYPE
	OBJECTS	{tControllerName, tSerNum, tTrapText}
	STATUS	current
	DESCRIPTION	"Protection 2. level - Mains/Bus >>V L2-L3 - alarm activated"
::= { notifications 159387904 }

tMainsCHR2FBusGtGtVL2L3L2Disappeared	NOTIFICATION-TYPE
	OBJECTS	{tControllerName, tSerNum, tTrapText}
	STATUS	current
	DESCRIPTION	"Protection 2. level - Mains/Bus >>V L2-L3 - alarm disappeared"
::= { notifications 159387905 }

tMainsCHR2FBusGtGtVL2L3L2AlarmReset	NOTIFICATION-TYPE
	OBJECTS	{tControllerName, tSerNum, tTrapText}
	STATUS	current
	DESCRIPTION	"Protection 2. level - Mains/Bus >>V L2-L3 - alarm reset"
::= { notifications 159387906 }

tMainsCHR2FBusLtLtVL2L3L2Activated	NOTIFICATION-TYPE
	OBJECTS	{tControllerName, tSerNum, tTrapText}
	STATUS	current
	DESCRIPTION	"Protection 2. level - Mains/Bus <<V L2-L3 - alarm activated"
::= { notifications 159387908 }

tMainsCHR2FBusLtLtVL2L3L2Disappeared	NOTIFICATION-TYPE
	OBJECTS	{tControllerName, tSerNum, tTrapText}
	STATUS	current
	DESCRIPTION	"Protection 2. level - Mains/Bus <<V L2-L3 - alarm disappeared"
::= { notifications 159387909 }

tMainsCHR2FBusLtLtVL2L3L2AlarmReset	NOTIFICATION-TYPE
	OBJECTS	{tControllerName, tSerNum, tTrapText}
	STATUS	current
	DESCRIPTION	"Protection 2. level - Mains/Bus <<V L2-L3 - alarm reset"
::= { notifications 159387910 }

tMainsCHR2FBusGtGtVL3L1L2Activated	NOTIFICATION-TYPE
	OBJECTS	{tControllerName, tSerNum, tTrapText}
	STATUS	current
	DESCRIPTION	"Protection 2. level - Mains/Bus >>V L3-L1 - alarm activated"
::= { notifications 159387912 }

tMainsCHR2FBusGtGtVL3L1L2Disappeared	NOTIFICATION-TYPE
	OBJECTS	{tControllerName, tSerNum, tTrapText}
	STATUS	current
	DESCRIPTION	"Protection 2. level - Mains/Bus >>V L3-L1 - alarm disappeared"
::= { notifications 159387913 }

tMainsCHR2FBusGtGtVL3L1L2AlarmReset	NOTIFICATION-TYPE
	OBJECTS	{tControllerName, tSerNum, tTrapText}
	STATUS	current
	DESCRIPTION	"Protection 2. level - Mains/Bus >>V L3-L1 - alarm reset"
::= { notifications 159387914 }

tMainsCHR2FBusLtLtVL3L1L2Activated	NOTIFICATION-TYPE
	OBJECTS	{tControllerName, tSerNum, tTrapText}
	STATUS	current
	DESCRIPTION	"Protection 2. level - Mains/Bus <<V L3-L1 - alarm activated"
::= { notifications 159387916 }

tMainsCHR2FBusLtLtVL3L1L2Disappeared	NOTIFICATION-TYPE
	OBJECTS	{tControllerName, tSerNum, tTrapText}
	STATUS	current
	DESCRIPTION	"Protection 2. level - Mains/Bus <<V L3-L1 - alarm disappeared"
::= { notifications 159387917 }

tMainsCHR2FBusLtLtVL3L1L2AlarmReset	NOTIFICATION-TYPE
	OBJECTS	{tControllerName, tSerNum, tTrapText}
	STATUS	current
	DESCRIPTION	"Protection 2. level - Mains/Bus <<V L3-L1 - alarm reset"
::= { notifications 159387918 }

tMainsCHR2FBus10minAvgGtVL1NL2Activated	NOTIFICATION-TYPE
	OBJECTS	{tControllerName, tSerNum, tTrapText}
	STATUS	current
	DESCRIPTION	"Protection 2. level - Mains/Bus 10min Avg >V L1-N - alarm activated"
::= { notifications 159389416 }

tMainsCHR2FBus10minAvgGtVL1NL2Disappeared	NOTIFICATION-TYPE
	OBJECTS	{tControllerName, tSerNum, tTrapText}
	STATUS	current
	DESCRIPTION	"Protection 2. level - Mains/Bus 10min Avg >V L1-N - alarm disappeared"
::= { notifications 159389417 }

tMainsCHR2FBus10minAvgGtVL1NL2AlarmReset	NOTIFICATION-TYPE
	OBJECTS	{tControllerName, tSerNum, tTrapText}
	STATUS	current
	DESCRIPTION	"Protection 2. level - Mains/Bus 10min Avg >V L1-N - alarm reset"
::= { notifications 159389418 }

tMainsCHR2FBus10minAvgGtVL2NL2Activated	NOTIFICATION-TYPE
	OBJECTS	{tControllerName, tSerNum, tTrapText}
	STATUS	current
	DESCRIPTION	"Protection 2. level - Mains/Bus 10min Avg >V L2-N - alarm activated"
::= { notifications 159389420 }

tMainsCHR2FBus10minAvgGtVL2NL2Disappeared	NOTIFICATION-TYPE
	OBJECTS	{tControllerName, tSerNum, tTrapText}
	STATUS	current
	DESCRIPTION	"Protection 2. level - Mains/Bus 10min Avg >V L2-N - alarm disappeared"
::= { notifications 159389421 }

tMainsCHR2FBus10minAvgGtVL2NL2AlarmReset	NOTIFICATION-TYPE
	OBJECTS	{tControllerName, tSerNum, tTrapText}
	STATUS	current
	DESCRIPTION	"Protection 2. level - Mains/Bus 10min Avg >V L2-N - alarm reset"
::= { notifications 159389422 }

tMainsCHR2FBus10minAvgGtVL3NL2Activated	NOTIFICATION-TYPE
	OBJECTS	{tControllerName, tSerNum, tTrapText}
	STATUS	current
	DESCRIPTION	"Protection 2. level - Mains/Bus 10min Avg >V L3-N - alarm activated"
::= { notifications 159389424 }

tMainsCHR2FBus10minAvgGtVL3NL2Disappeared	NOTIFICATION-TYPE
	OBJECTS	{tControllerName, tSerNum, tTrapText}
	STATUS	current
	DESCRIPTION	"Protection 2. level - Mains/Bus 10min Avg >V L3-N - alarm disappeared"
::= { notifications 159389425 }

tMainsCHR2FBus10minAvgGtVL3NL2AlarmReset	NOTIFICATION-TYPE
	OBJECTS	{tControllerName, tSerNum, tTrapText}
	STATUS	current
	DESCRIPTION	"Protection 2. level - Mains/Bus 10min Avg >V L3-N - alarm reset"
::= { notifications 159389426 }

tMainsCHR2FBus10minAvgGtVL1L2L2Activated	NOTIFICATION-TYPE
	OBJECTS	{tControllerName, tSerNum, tTrapText}
	STATUS	current
	DESCRIPTION	"Protection 2. level - Mains/Bus 10min Avg >V L1-L2 - alarm activated"
::= { notifications 159388128 }

tMainsCHR2FBus10minAvgGtVL1L2L2Disappeared	NOTIFICATION-TYPE
	OBJECTS	{tControllerName, tSerNum, tTrapText}
	STATUS	current
	DESCRIPTION	"Protection 2. level - Mains/Bus 10min Avg >V L1-L2 - alarm disappeared"
::= { notifications 159388129 }

tMainsCHR2FBus10minAvgGtVL1L2L2AlarmReset	NOTIFICATION-TYPE
	OBJECTS	{tControllerName, tSerNum, tTrapText}
	STATUS	current
	DESCRIPTION	"Protection 2. level - Mains/Bus 10min Avg >V L1-L2 - alarm reset"
::= { notifications 159388130 }

tMainsCHR2FBus10minAvgGtVL2L3L2Activated	NOTIFICATION-TYPE
	OBJECTS	{tControllerName, tSerNum, tTrapText}
	STATUS	current
	DESCRIPTION	"Protection 2. level - Mains/Bus 10min Avg >V L2-L3 - alarm activated"
::= { notifications 159388132 }

tMainsCHR2FBus10minAvgGtVL2L3L2Disappeared	NOTIFICATION-TYPE
	OBJECTS	{tControllerName, tSerNum, tTrapText}
	STATUS	current
	DESCRIPTION	"Protection 2. level - Mains/Bus 10min Avg >V L2-L3 - alarm disappeared"
::= { notifications 159388133 }

tMainsCHR2FBus10minAvgGtVL2L3L2AlarmReset	NOTIFICATION-TYPE
	OBJECTS	{tControllerName, tSerNum, tTrapText}
	STATUS	current
	DESCRIPTION	"Protection 2. level - Mains/Bus 10min Avg >V L2-L3 - alarm reset"
::= { notifications 159388134 }

tMainsCHR2FBus10minAvgGtVL3L1L2Activated	NOTIFICATION-TYPE
	OBJECTS	{tControllerName, tSerNum, tTrapText}
	STATUS	current
	DESCRIPTION	"Protection 2. level - Mains/Bus 10min Avg >V L3-L1 - alarm activated"
::= { notifications 159388136 }

tMainsCHR2FBus10minAvgGtVL3L1L2Disappeared	NOTIFICATION-TYPE
	OBJECTS	{tControllerName, tSerNum, tTrapText}
	STATUS	current
	DESCRIPTION	"Protection 2. level - Mains/Bus 10min Avg >V L3-L1 - alarm disappeared"
::= { notifications 159388137 }

tMainsCHR2FBus10minAvgGtVL3L1L2AlarmReset	NOTIFICATION-TYPE
	OBJECTS	{tControllerName, tSerNum, tTrapText}
	STATUS	current
	DESCRIPTION	"Protection 2. level - Mains/Bus 10min Avg >V L3-L1 - alarm reset"
::= { notifications 159388138 }

tMainsCHR2FBusVUnbalancePhPhL2Activated2	NOTIFICATION-TYPE
	OBJECTS	{tControllerName, tSerNum, tTrapText}
	STATUS	current
	DESCRIPTION	"Protection 2. level - Mains/Bus V Unbalance Ph-Ph - alarm activated"
::= { notifications 159385920 }

tMainsCHR2FBusVUnbalancePhPhL2Disappeared2	NOTIFICATION-TYPE
	OBJECTS	{tControllerName, tSerNum, tTrapText}
	STATUS	current
	DESCRIPTION	"Protection 2. level - Mains/Bus V Unbalance Ph-Ph - alarm disappeared"
::= { notifications 159385921 }

tMainsCHR2FBusVUnbalancePhPhL2AlarmReset2	NOTIFICATION-TYPE
	OBJECTS	{tControllerName, tSerNum, tTrapText}
	STATUS	current
	DESCRIPTION	"Protection 2. level - Mains/Bus V Unbalance Ph-Ph - alarm reset"
::= { notifications 159385922 }

tMainsCHR2FBusVUnbalancePhNL2Activated2	NOTIFICATION-TYPE
	OBJECTS	{tControllerName, tSerNum, tTrapText}
	STATUS	current
	DESCRIPTION	"Protection 2. level - Mains/Bus V Unbalance Ph-N - alarm activated"
::= { notifications 159385924 }

tMainsCHR2FBusVUnbalancePhNL2Disappeared2	NOTIFICATION-TYPE
	OBJECTS	{tControllerName, tSerNum, tTrapText}
	STATUS	current
	DESCRIPTION	"Protection 2. level - Mains/Bus V Unbalance Ph-N - alarm disappeared"
::= { notifications 159385925 }

tMainsCHR2FBusVUnbalancePhNL2AlarmReset2	NOTIFICATION-TYPE
	OBJECTS	{tControllerName, tSerNum, tTrapText}
	STATUS	current
	DESCRIPTION	"Protection 2. level - Mains/Bus V Unbalance Ph-N - alarm reset"
::= { notifications 159385926 }

tMainsCHR2FBusGtFL2Activated	NOTIFICATION-TYPE
	OBJECTS	{tControllerName, tSerNum, tTrapText}
	STATUS	current
	DESCRIPTION	"Protection 2. level - Mains/Bus >f - alarm activated"
::= { notifications 159384092 }

tMainsCHR2FBusGtFL2Disappeared	NOTIFICATION-TYPE
	OBJECTS	{tControllerName, tSerNum, tTrapText}
	STATUS	current
	DESCRIPTION	"Protection 2. level - Mains/Bus >f - alarm disappeared"
::= { notifications 159384093 }

tMainsCHR2FBusGtFL2AlarmReset	NOTIFICATION-TYPE
	OBJECTS	{tControllerName, tSerNum, tTrapText}
	STATUS	current
	DESCRIPTION	"Protection 2. level - Mains/Bus >f - alarm reset"
::= { notifications 159384094 }

tMainsCHR2FBusLtFL2Activated	NOTIFICATION-TYPE
	OBJECTS	{tControllerName, tSerNum, tTrapText}
	STATUS	current
	DESCRIPTION	"Protection 2. level - Mains/Bus <f - alarm activated"
::= { notifications 159384088 }

tMainsCHR2FBusLtFL2Disappeared	NOTIFICATION-TYPE
	OBJECTS	{tControllerName, tSerNum, tTrapText}
	STATUS	current
	DESCRIPTION	"Protection 2. level - Mains/Bus <f - alarm disappeared"
::= { notifications 159384089 }

tMainsCHR2FBusLtFL2AlarmReset	NOTIFICATION-TYPE
	OBJECTS	{tControllerName, tSerNum, tTrapText}
	STATUS	current
	DESCRIPTION	"Protection 2. level - Mains/Bus <f - alarm reset"
::= { notifications 159384090 }

tMainsCHR2FBusGtGtFL2Activated	NOTIFICATION-TYPE
	OBJECTS	{tControllerName, tSerNum, tTrapText}
	STATUS	current
	DESCRIPTION	"Protection 2. level - Mains/Bus >>f - alarm activated"
::= { notifications 159387920 }

tMainsCHR2FBusGtGtFL2Disappeared	NOTIFICATION-TYPE
	OBJECTS	{tControllerName, tSerNum, tTrapText}
	STATUS	current
	DESCRIPTION	"Protection 2. level - Mains/Bus >>f - alarm disappeared"
::= { notifications 159387921 }

tMainsCHR2FBusGtGtFL2AlarmReset	NOTIFICATION-TYPE
	OBJECTS	{tControllerName, tSerNum, tTrapText}
	STATUS	current
	DESCRIPTION	"Protection 2. level - Mains/Bus >>f - alarm reset"
::= { notifications 159387922 }

tMainsCHR2FBusLtLtFL2Activated	NOTIFICATION-TYPE
	OBJECTS	{tControllerName, tSerNum, tTrapText}
	STATUS	current
	DESCRIPTION	"Protection 2. level - Mains/Bus <<f - alarm activated"
::= { notifications 159387924 }

tMainsCHR2FBusLtLtFL2Disappeared	NOTIFICATION-TYPE
	OBJECTS	{tControllerName, tSerNum, tTrapText}
	STATUS	current
	DESCRIPTION	"Protection 2. level - Mains/Bus <<f - alarm disappeared"
::= { notifications 159387925 }

tMainsCHR2FBusLtLtFL2AlarmReset	NOTIFICATION-TYPE
	OBJECTS	{tControllerName, tSerNum, tTrapText}
	STATUS	current
	DESCRIPTION	"Protection 2. level - Mains/Bus <<f - alarm reset"
::= { notifications 159387926 }

tVRTUm1OVRTL1Activated	NOTIFICATION-TYPE
	OBJECTS	{tControllerName, tSerNum, tTrapText}
	STATUS	current
	DESCRIPTION	"Protection 1. level - VRT Um1 OVRT - alarm activated"
::= { notifications 25170348 }

tVRTUm1OVRTL1Disappeared	NOTIFICATION-TYPE
	OBJECTS	{tControllerName, tSerNum, tTrapText}
	STATUS	current
	DESCRIPTION	"Protection 1. level - VRT Um1 OVRT - alarm disappeared"
::= { notifications 25170349 }

tVRTUm1OVRTL1AlarmReset	NOTIFICATION-TYPE
	OBJECTS	{tControllerName, tSerNum, tTrapText}
	STATUS	current
	DESCRIPTION	"Protection 1. level - VRT Um1 OVRT - alarm reset"
::= { notifications 25170350 }

tVRTUm1OVRTL2Activated	NOTIFICATION-TYPE
	OBJECTS	{tControllerName, tSerNum, tTrapText}
	STATUS	current
	DESCRIPTION	"Protection 2. level - VRT Um1 OVRT - alarm activated"
::= { notifications 159388076 }

tVRTUm1OVRTL2Disappeared	NOTIFICATION-TYPE
	OBJECTS	{tControllerName, tSerNum, tTrapText}
	STATUS	current
	DESCRIPTION	"Protection 2. level - VRT Um1 OVRT - alarm disappeared"
::= { notifications 159388077 }

tVRTUm1OVRTL2AlarmReset	NOTIFICATION-TYPE
	OBJECTS	{tControllerName, tSerNum, tTrapText}
	STATUS	current
	DESCRIPTION	"Protection 2. level - VRT Um1 OVRT - alarm reset"
::= { notifications 159388078 }

tVRTUm1OVRTSFActivated	NOTIFICATION-TYPE
	OBJECTS	{tControllerName, tSerNum, tTrapText}
	STATUS	current
	DESCRIPTION	"Protection Sensor Fail - VRT Um1 OVRT - alarm activated"
::= { notifications 293605804 }

tVRTUm1OVRTSFDisappeared	NOTIFICATION-TYPE
	OBJECTS	{tControllerName, tSerNum, tTrapText}
	STATUS	current
	DESCRIPTION	"Protection Sensor Fail - VRT Um1 OVRT - alarm disappeared"
::= { notifications 293605805 }

tVRTUm1OVRTSFAlarmReset	NOTIFICATION-TYPE
	OBJECTS	{tControllerName, tSerNum, tTrapText}
	STATUS	current
	DESCRIPTION	"Protection Sensor Fail - VRT Um1 OVRT - alarm reset"
::= { notifications 293605806 }

tVRTUm1LVRT1L1Activated	NOTIFICATION-TYPE
	OBJECTS	{tControllerName, tSerNum, tTrapText}
	STATUS	current
	DESCRIPTION	"Protection 1. level - VRT Um1 LVRT1 - alarm activated"
::= { notifications 25170352 }

tVRTUm1LVRT1L1Disappeared	NOTIFICATION-TYPE
	OBJECTS	{tControllerName, tSerNum, tTrapText}
	STATUS	current
	DESCRIPTION	"Protection 1. level - VRT Um1 LVRT1 - alarm disappeared"
::= { notifications 25170353 }

tVRTUm1LVRT1L1AlarmReset	NOTIFICATION-TYPE
	OBJECTS	{tControllerName, tSerNum, tTrapText}
	STATUS	current
	DESCRIPTION	"Protection 1. level - VRT Um1 LVRT1 - alarm reset"
::= { notifications 25170354 }

tVRTUm1LVRT1L2Activated	NOTIFICATION-TYPE
	OBJECTS	{tControllerName, tSerNum, tTrapText}
	STATUS	current
	DESCRIPTION	"Protection 2. level - VRT Um1 LVRT1 - alarm activated"
::= { notifications 159388080 }

tVRTUm1LVRT1L2Disappeared	NOTIFICATION-TYPE
	OBJECTS	{tControllerName, tSerNum, tTrapText}
	STATUS	current
	DESCRIPTION	"Protection 2. level - VRT Um1 LVRT1 - alarm disappeared"
::= { notifications 159388081 }

tVRTUm1LVRT1L2AlarmReset	NOTIFICATION-TYPE
	OBJECTS	{tControllerName, tSerNum, tTrapText}
	STATUS	current
	DESCRIPTION	"Protection 2. level - VRT Um1 LVRT1 - alarm reset"
::= { notifications 159388082 }

tVRTUm1LVRT1SFActivated	NOTIFICATION-TYPE
	OBJECTS	{tControllerName, tSerNum, tTrapText}
	STATUS	current
	DESCRIPTION	"Protection Sensor Fail - VRT Um1 LVRT1 - alarm activated"
::= { notifications 293605808 }

tVRTUm1LVRT1SFDisappeared	NOTIFICATION-TYPE
	OBJECTS	{tControllerName, tSerNum, tTrapText}
	STATUS	current
	DESCRIPTION	"Protection Sensor Fail - VRT Um1 LVRT1 - alarm disappeared"
::= { notifications 293605809 }

tVRTUm1LVRT1SFAlarmReset	NOTIFICATION-TYPE
	OBJECTS	{tControllerName, tSerNum, tTrapText}
	STATUS	current
	DESCRIPTION	"Protection Sensor Fail - VRT Um1 LVRT1 - alarm reset"
::= { notifications 293605810 }

tVRTUm1LVRT2L1Activated	NOTIFICATION-TYPE
	OBJECTS	{tControllerName, tSerNum, tTrapText}
	STATUS	current
	DESCRIPTION	"Protection 1. level - VRT Um1 LVRT2 - alarm activated"
::= { notifications 25170356 }

tVRTUm1LVRT2L1Disappeared	NOTIFICATION-TYPE
	OBJECTS	{tControllerName, tSerNum, tTrapText}
	STATUS	current
	DESCRIPTION	"Protection 1. level - VRT Um1 LVRT2 - alarm disappeared"
::= { notifications 25170357 }

tVRTUm1LVRT2L1AlarmReset	NOTIFICATION-TYPE
	OBJECTS	{tControllerName, tSerNum, tTrapText}
	STATUS	current
	DESCRIPTION	"Protection 1. level - VRT Um1 LVRT2 - alarm reset"
::= { notifications 25170358 }

tVRTUm1LVRT2L2Activated	NOTIFICATION-TYPE
	OBJECTS	{tControllerName, tSerNum, tTrapText}
	STATUS	current
	DESCRIPTION	"Protection 2. level - VRT Um1 LVRT2 - alarm activated"
::= { notifications 159388084 }

tVRTUm1LVRT2L2Disappeared	NOTIFICATION-TYPE
	OBJECTS	{tControllerName, tSerNum, tTrapText}
	STATUS	current
	DESCRIPTION	"Protection 2. level - VRT Um1 LVRT2 - alarm disappeared"
::= { notifications 159388085 }

tVRTUm1LVRT2L2AlarmReset	NOTIFICATION-TYPE
	OBJECTS	{tControllerName, tSerNum, tTrapText}
	STATUS	current
	DESCRIPTION	"Protection 2. level - VRT Um1 LVRT2 - alarm reset"
::= { notifications 159388086 }

tVRTUm1LVRT2SFActivated	NOTIFICATION-TYPE
	OBJECTS	{tControllerName, tSerNum, tTrapText}
	STATUS	current
	DESCRIPTION	"Protection Sensor Fail - VRT Um1 LVRT2 - alarm activated"
::= { notifications 293605812 }

tVRTUm1LVRT2SFDisappeared	NOTIFICATION-TYPE
	OBJECTS	{tControllerName, tSerNum, tTrapText}
	STATUS	current
	DESCRIPTION	"Protection Sensor Fail - VRT Um1 LVRT2 - alarm disappeared"
::= { notifications 293605813 }

tVRTUm1LVRT2SFAlarmReset	NOTIFICATION-TYPE
	OBJECTS	{tControllerName, tSerNum, tTrapText}
	STATUS	current
	DESCRIPTION	"Protection Sensor Fail - VRT Um1 LVRT2 - alarm reset"
::= { notifications 293605814 }

tVRTUm1LVRT3L1Activated	NOTIFICATION-TYPE
	OBJECTS	{tControllerName, tSerNum, tTrapText}
	STATUS	current
	DESCRIPTION	"Protection 1. level - VRT Um1 LVRT3 - alarm activated"
::= { notifications 25170360 }

tVRTUm1LVRT3L1Disappeared	NOTIFICATION-TYPE
	OBJECTS	{tControllerName, tSerNum, tTrapText}
	STATUS	current
	DESCRIPTION	"Protection 1. level - VRT Um1 LVRT3 - alarm disappeared"
::= { notifications 25170361 }

tVRTUm1LVRT3L1AlarmReset	NOTIFICATION-TYPE
	OBJECTS	{tControllerName, tSerNum, tTrapText}
	STATUS	current
	DESCRIPTION	"Protection 1. level - VRT Um1 LVRT3 - alarm reset"
::= { notifications 25170362 }

tVRTUm1LVRT3L2Activated	NOTIFICATION-TYPE
	OBJECTS	{tControllerName, tSerNum, tTrapText}
	STATUS	current
	DESCRIPTION	"Protection 2. level - VRT Um1 LVRT3 - alarm activated"
::= { notifications 159388088 }

tVRTUm1LVRT3L2Disappeared	NOTIFICATION-TYPE
	OBJECTS	{tControllerName, tSerNum, tTrapText}
	STATUS	current
	DESCRIPTION	"Protection 2. level - VRT Um1 LVRT3 - alarm disappeared"
::= { notifications 159388089 }

tVRTUm1LVRT3L2AlarmReset	NOTIFICATION-TYPE
	OBJECTS	{tControllerName, tSerNum, tTrapText}
	STATUS	current
	DESCRIPTION	"Protection 2. level - VRT Um1 LVRT3 - alarm reset"
::= { notifications 159388090 }

tVRTUm1LVRT3SFActivated	NOTIFICATION-TYPE
	OBJECTS	{tControllerName, tSerNum, tTrapText}
	STATUS	current
	DESCRIPTION	"Protection Sensor Fail - VRT Um1 LVRT3 - alarm activated"
::= { notifications 293605816 }

tVRTUm1LVRT3SFDisappeared	NOTIFICATION-TYPE
	OBJECTS	{tControllerName, tSerNum, tTrapText}
	STATUS	current
	DESCRIPTION	"Protection Sensor Fail - VRT Um1 LVRT3 - alarm disappeared"
::= { notifications 293605817 }

tVRTUm1LVRT3SFAlarmReset	NOTIFICATION-TYPE
	OBJECTS	{tControllerName, tSerNum, tTrapText}
	STATUS	current
	DESCRIPTION	"Protection Sensor Fail - VRT Um1 LVRT3 - alarm reset"
::= { notifications 293605818 }

tVRTUm2OVRTL1Activated	NOTIFICATION-TYPE
	OBJECTS	{tControllerName, tSerNum, tTrapText}
	STATUS	current
	DESCRIPTION	"Protection 1. level - VRT Um2 OVRT - alarm activated"
::= { notifications 25170364 }

tVRTUm2OVRTL1Disappeared	NOTIFICATION-TYPE
	OBJECTS	{tControllerName, tSerNum, tTrapText}
	STATUS	current
	DESCRIPTION	"Protection 1. level - VRT Um2 OVRT - alarm disappeared"
::= { notifications 25170365 }

tVRTUm2OVRTL1AlarmReset	NOTIFICATION-TYPE
	OBJECTS	{tControllerName, tSerNum, tTrapText}
	STATUS	current
	DESCRIPTION	"Protection 1. level - VRT Um2 OVRT - alarm reset"
::= { notifications 25170366 }

tVRTUm2OVRTL2Activated	NOTIFICATION-TYPE
	OBJECTS	{tControllerName, tSerNum, tTrapText}
	STATUS	current
	DESCRIPTION	"Protection 2. level - VRT Um2 OVRT - alarm activated"
::= { notifications 159388092 }

tVRTUm2OVRTL2Disappeared	NOTIFICATION-TYPE
	OBJECTS	{tControllerName, tSerNum, tTrapText}
	STATUS	current
	DESCRIPTION	"Protection 2. level - VRT Um2 OVRT - alarm disappeared"
::= { notifications 159388093 }

tVRTUm2OVRTL2AlarmReset	NOTIFICATION-TYPE
	OBJECTS	{tControllerName, tSerNum, tTrapText}
	STATUS	current
	DESCRIPTION	"Protection 2. level - VRT Um2 OVRT - alarm reset"
::= { notifications 159388094 }

tVRTUm2OVRTSFActivated	NOTIFICATION-TYPE
	OBJECTS	{tControllerName, tSerNum, tTrapText}
	STATUS	current
	DESCRIPTION	"Protection Sensor Fail - VRT Um2 OVRT - alarm activated"
::= { notifications 293605820 }

tVRTUm2OVRTSFDisappeared	NOTIFICATION-TYPE
	OBJECTS	{tControllerName, tSerNum, tTrapText}
	STATUS	current
	DESCRIPTION	"Protection Sensor Fail - VRT Um2 OVRT - alarm disappeared"
::= { notifications 293605821 }

tVRTUm2OVRTSFAlarmReset	NOTIFICATION-TYPE
	OBJECTS	{tControllerName, tSerNum, tTrapText}
	STATUS	current
	DESCRIPTION	"Protection Sensor Fail - VRT Um2 OVRT - alarm reset"
::= { notifications 293605822 }

tVRTUm2LVRT1L1Activated	NOTIFICATION-TYPE
	OBJECTS	{tControllerName, tSerNum, tTrapText}
	STATUS	current
	DESCRIPTION	"Protection 1. level - VRT Um2 LVRT1 - alarm activated"
::= { notifications 25170368 }

tVRTUm2LVRT1L1Disappeared	NOTIFICATION-TYPE
	OBJECTS	{tControllerName, tSerNum, tTrapText}
	STATUS	current
	DESCRIPTION	"Protection 1. level - VRT Um2 LVRT1 - alarm disappeared"
::= { notifications 25170369 }

tVRTUm2LVRT1L1AlarmReset	NOTIFICATION-TYPE
	OBJECTS	{tControllerName, tSerNum, tTrapText}
	STATUS	current
	DESCRIPTION	"Protection 1. level - VRT Um2 LVRT1 - alarm reset"
::= { notifications 25170370 }

tVRTUm2LVRT1L2Activated	NOTIFICATION-TYPE
	OBJECTS	{tControllerName, tSerNum, tTrapText}
	STATUS	current
	DESCRIPTION	"Protection 2. level - VRT Um2 LVRT1 - alarm activated"
::= { notifications 159388096 }

tVRTUm2LVRT1L2Disappeared	NOTIFICATION-TYPE
	OBJECTS	{tControllerName, tSerNum, tTrapText}
	STATUS	current
	DESCRIPTION	"Protection 2. level - VRT Um2 LVRT1 - alarm disappeared"
::= { notifications 159388097 }

tVRTUm2LVRT1L2AlarmReset	NOTIFICATION-TYPE
	OBJECTS	{tControllerName, tSerNum, tTrapText}
	STATUS	current
	DESCRIPTION	"Protection 2. level - VRT Um2 LVRT1 - alarm reset"
::= { notifications 159388098 }

tVRTUm2LVRT1SFActivated	NOTIFICATION-TYPE
	OBJECTS	{tControllerName, tSerNum, tTrapText}
	STATUS	current
	DESCRIPTION	"Protection Sensor Fail - VRT Um2 LVRT1 - alarm activated"
::= { notifications 293605824 }

tVRTUm2LVRT1SFDisappeared	NOTIFICATION-TYPE
	OBJECTS	{tControllerName, tSerNum, tTrapText}
	STATUS	current
	DESCRIPTION	"Protection Sensor Fail - VRT Um2 LVRT1 - alarm disappeared"
::= { notifications 293605825 }

tVRTUm2LVRT1SFAlarmReset	NOTIFICATION-TYPE
	OBJECTS	{tControllerName, tSerNum, tTrapText}
	STATUS	current
	DESCRIPTION	"Protection Sensor Fail - VRT Um2 LVRT1 - alarm reset"
::= { notifications 293605826 }

tVRTUm2LVRT2L1Activated	NOTIFICATION-TYPE
	OBJECTS	{tControllerName, tSerNum, tTrapText}
	STATUS	current
	DESCRIPTION	"Protection 1. level - VRT Um2 LVRT2 - alarm activated"
::= { notifications 25170372 }

tVRTUm2LVRT2L1Disappeared	NOTIFICATION-TYPE
	OBJECTS	{tControllerName, tSerNum, tTrapText}
	STATUS	current
	DESCRIPTION	"Protection 1. level - VRT Um2 LVRT2 - alarm disappeared"
::= { notifications 25170373 }

tVRTUm2LVRT2L1AlarmReset	NOTIFICATION-TYPE
	OBJECTS	{tControllerName, tSerNum, tTrapText}
	STATUS	current
	DESCRIPTION	"Protection 1. level - VRT Um2 LVRT2 - alarm reset"
::= { notifications 25170374 }

tVRTUm2LVRT2L2Activated	NOTIFICATION-TYPE
	OBJECTS	{tControllerName, tSerNum, tTrapText}
	STATUS	current
	DESCRIPTION	"Protection 2. level - VRT Um2 LVRT2 - alarm activated"
::= { notifications 159388100 }

tVRTUm2LVRT2L2Disappeared	NOTIFICATION-TYPE
	OBJECTS	{tControllerName, tSerNum, tTrapText}
	STATUS	current
	DESCRIPTION	"Protection 2. level - VRT Um2 LVRT2 - alarm disappeared"
::= { notifications 159388101 }

tVRTUm2LVRT2L2AlarmReset	NOTIFICATION-TYPE
	OBJECTS	{tControllerName, tSerNum, tTrapText}
	STATUS	current
	DESCRIPTION	"Protection 2. level - VRT Um2 LVRT2 - alarm reset"
::= { notifications 159388102 }

tVRTUm2LVRT2SFActivated	NOTIFICATION-TYPE
	OBJECTS	{tControllerName, tSerNum, tTrapText}
	STATUS	current
	DESCRIPTION	"Protection Sensor Fail - VRT Um2 LVRT2 - alarm activated"
::= { notifications 293605828 }

tVRTUm2LVRT2SFDisappeared	NOTIFICATION-TYPE
	OBJECTS	{tControllerName, tSerNum, tTrapText}
	STATUS	current
	DESCRIPTION	"Protection Sensor Fail - VRT Um2 LVRT2 - alarm disappeared"
::= { notifications 293605829 }

tVRTUm2LVRT2SFAlarmReset	NOTIFICATION-TYPE
	OBJECTS	{tControllerName, tSerNum, tTrapText}
	STATUS	current
	DESCRIPTION	"Protection Sensor Fail - VRT Um2 LVRT2 - alarm reset"
::= { notifications 293605830 }

tVRTUm2LVRT3L1Activated	NOTIFICATION-TYPE
	OBJECTS	{tControllerName, tSerNum, tTrapText}
	STATUS	current
	DESCRIPTION	"Protection 1. level - VRT Um2 LVRT3 - alarm activated"
::= { notifications 25170376 }

tVRTUm2LVRT3L1Disappeared	NOTIFICATION-TYPE
	OBJECTS	{tControllerName, tSerNum, tTrapText}
	STATUS	current
	DESCRIPTION	"Protection 1. level - VRT Um2 LVRT3 - alarm disappeared"
::= { notifications 25170377 }

tVRTUm2LVRT3L1AlarmReset	NOTIFICATION-TYPE
	OBJECTS	{tControllerName, tSerNum, tTrapText}
	STATUS	current
	DESCRIPTION	"Protection 1. level - VRT Um2 LVRT3 - alarm reset"
::= { notifications 25170378 }

tVRTUm2LVRT3L2Activated	NOTIFICATION-TYPE
	OBJECTS	{tControllerName, tSerNum, tTrapText}
	STATUS	current
	DESCRIPTION	"Protection 2. level - VRT Um2 LVRT3 - alarm activated"
::= { notifications 159388104 }

tVRTUm2LVRT3L2Disappeared	NOTIFICATION-TYPE
	OBJECTS	{tControllerName, tSerNum, tTrapText}
	STATUS	current
	DESCRIPTION	"Protection 2. level - VRT Um2 LVRT3 - alarm disappeared"
::= { notifications 159388105 }

tVRTUm2LVRT3L2AlarmReset	NOTIFICATION-TYPE
	OBJECTS	{tControllerName, tSerNum, tTrapText}
	STATUS	current
	DESCRIPTION	"Protection 2. level - VRT Um2 LVRT3 - alarm reset"
::= { notifications 159388106 }

tVRTUm2LVRT3SFActivated	NOTIFICATION-TYPE
	OBJECTS	{tControllerName, tSerNum, tTrapText}
	STATUS	current
	DESCRIPTION	"Protection Sensor Fail - VRT Um2 LVRT3 - alarm activated"
::= { notifications 293605832 }

tVRTUm2LVRT3SFDisappeared	NOTIFICATION-TYPE
	OBJECTS	{tControllerName, tSerNum, tTrapText}
	STATUS	current
	DESCRIPTION	"Protection Sensor Fail - VRT Um2 LVRT3 - alarm disappeared"
::= { notifications 293605833 }

tVRTUm2LVRT3SFAlarmReset	NOTIFICATION-TYPE
	OBJECTS	{tControllerName, tSerNum, tTrapText}
	STATUS	current
	DESCRIPTION	"Protection Sensor Fail - VRT Um2 LVRT3 - alarm reset"
::= { notifications 293605834 }

tVRTUm3OVRTL1Activated	NOTIFICATION-TYPE
	OBJECTS	{tControllerName, tSerNum, tTrapText}
	STATUS	current
	DESCRIPTION	"Protection 1. level - VRT Um3 OVRT - alarm activated"
::= { notifications 25170380 }

tVRTUm3OVRTL1Disappeared	NOTIFICATION-TYPE
	OBJECTS	{tControllerName, tSerNum, tTrapText}
	STATUS	current
	DESCRIPTION	"Protection 1. level - VRT Um3 OVRT - alarm disappeared"
::= { notifications 25170381 }

tVRTUm3OVRTL1AlarmReset	NOTIFICATION-TYPE
	OBJECTS	{tControllerName, tSerNum, tTrapText}
	STATUS	current
	DESCRIPTION	"Protection 1. level - VRT Um3 OVRT - alarm reset"
::= { notifications 25170382 }

tVRTUm3OVRTL2Activated	NOTIFICATION-TYPE
	OBJECTS	{tControllerName, tSerNum, tTrapText}
	STATUS	current
	DESCRIPTION	"Protection 2. level - VRT Um3 OVRT - alarm activated"
::= { notifications 159388108 }

tVRTUm3OVRTL2Disappeared	NOTIFICATION-TYPE
	OBJECTS	{tControllerName, tSerNum, tTrapText}
	STATUS	current
	DESCRIPTION	"Protection 2. level - VRT Um3 OVRT - alarm disappeared"
::= { notifications 159388109 }

tVRTUm3OVRTL2AlarmReset	NOTIFICATION-TYPE
	OBJECTS	{tControllerName, tSerNum, tTrapText}
	STATUS	current
	DESCRIPTION	"Protection 2. level - VRT Um3 OVRT - alarm reset"
::= { notifications 159388110 }

tVRTUm3OVRTSFActivated	NOTIFICATION-TYPE
	OBJECTS	{tControllerName, tSerNum, tTrapText}
	STATUS	current
	DESCRIPTION	"Protection Sensor Fail - VRT Um3 OVRT - alarm activated"
::= { notifications 293605836 }

tVRTUm3OVRTSFDisappeared	NOTIFICATION-TYPE
	OBJECTS	{tControllerName, tSerNum, tTrapText}
	STATUS	current
	DESCRIPTION	"Protection Sensor Fail - VRT Um3 OVRT - alarm disappeared"
::= { notifications 293605837 }

tVRTUm3OVRTSFAlarmReset	NOTIFICATION-TYPE
	OBJECTS	{tControllerName, tSerNum, tTrapText}
	STATUS	current
	DESCRIPTION	"Protection Sensor Fail - VRT Um3 OVRT - alarm reset"
::= { notifications 293605838 }

tVRTUm3LVRT1L1Activated	NOTIFICATION-TYPE
	OBJECTS	{tControllerName, tSerNum, tTrapText}
	STATUS	current
	DESCRIPTION	"Protection 1. level - VRT Um3 LVRT1 - alarm activated"
::= { notifications 25170384 }

tVRTUm3LVRT1L1Disappeared	NOTIFICATION-TYPE
	OBJECTS	{tControllerName, tSerNum, tTrapText}
	STATUS	current
	DESCRIPTION	"Protection 1. level - VRT Um3 LVRT1 - alarm disappeared"
::= { notifications 25170385 }

tVRTUm3LVRT1L1AlarmReset	NOTIFICATION-TYPE
	OBJECTS	{tControllerName, tSerNum, tTrapText}
	STATUS	current
	DESCRIPTION	"Protection 1. level - VRT Um3 LVRT1 - alarm reset"
::= { notifications 25170386 }

tVRTUm3LVRT1L2Activated	NOTIFICATION-TYPE
	OBJECTS	{tControllerName, tSerNum, tTrapText}
	STATUS	current
	DESCRIPTION	"Protection 2. level - VRT Um3 LVRT1 - alarm activated"
::= { notifications 159388112 }

tVRTUm3LVRT1L2Disappeared	NOTIFICATION-TYPE
	OBJECTS	{tControllerName, tSerNum, tTrapText}
	STATUS	current
	DESCRIPTION	"Protection 2. level - VRT Um3 LVRT1 - alarm disappeared"
::= { notifications 159388113 }

tVRTUm3LVRT1L2AlarmReset	NOTIFICATION-TYPE
	OBJECTS	{tControllerName, tSerNum, tTrapText}
	STATUS	current
	DESCRIPTION	"Protection 2. level - VRT Um3 LVRT1 - alarm reset"
::= { notifications 159388114 }

tVRTUm3LVRT1SFActivated	NOTIFICATION-TYPE
	OBJECTS	{tControllerName, tSerNum, tTrapText}
	STATUS	current
	DESCRIPTION	"Protection Sensor Fail - VRT Um3 LVRT1 - alarm activated"
::= { notifications 293605840 }

tVRTUm3LVRT1SFDisappeared	NOTIFICATION-TYPE
	OBJECTS	{tControllerName, tSerNum, tTrapText}
	STATUS	current
	DESCRIPTION	"Protection Sensor Fail - VRT Um3 LVRT1 - alarm disappeared"
::= { notifications 293605841 }

tVRTUm3LVRT1SFAlarmReset	NOTIFICATION-TYPE
	OBJECTS	{tControllerName, tSerNum, tTrapText}
	STATUS	current
	DESCRIPTION	"Protection Sensor Fail - VRT Um3 LVRT1 - alarm reset"
::= { notifications 293605842 }

tVRTUm3LVRT2L1Activated	NOTIFICATION-TYPE
	OBJECTS	{tControllerName, tSerNum, tTrapText}
	STATUS	current
	DESCRIPTION	"Protection 1. level - VRT Um3 LVRT2 - alarm activated"
::= { notifications 25170388 }

tVRTUm3LVRT2L1Disappeared	NOTIFICATION-TYPE
	OBJECTS	{tControllerName, tSerNum, tTrapText}
	STATUS	current
	DESCRIPTION	"Protection 1. level - VRT Um3 LVRT2 - alarm disappeared"
::= { notifications 25170389 }

tVRTUm3LVRT2L1AlarmReset	NOTIFICATION-TYPE
	OBJECTS	{tControllerName, tSerNum, tTrapText}
	STATUS	current
	DESCRIPTION	"Protection 1. level - VRT Um3 LVRT2 - alarm reset"
::= { notifications 25170390 }

tVRTUm3LVRT2L2Activated	NOTIFICATION-TYPE
	OBJECTS	{tControllerName, tSerNum, tTrapText}
	STATUS	current
	DESCRIPTION	"Protection 2. level - VRT Um3 LVRT2 - alarm activated"
::= { notifications 159388116 }

tVRTUm3LVRT2L2Disappeared	NOTIFICATION-TYPE
	OBJECTS	{tControllerName, tSerNum, tTrapText}
	STATUS	current
	DESCRIPTION	"Protection 2. level - VRT Um3 LVRT2 - alarm disappeared"
::= { notifications 159388117 }

tVRTUm3LVRT2L2AlarmReset	NOTIFICATION-TYPE
	OBJECTS	{tControllerName, tSerNum, tTrapText}
	STATUS	current
	DESCRIPTION	"Protection 2. level - VRT Um3 LVRT2 - alarm reset"
::= { notifications 159388118 }

tVRTUm3LVRT2SFActivated	NOTIFICATION-TYPE
	OBJECTS	{tControllerName, tSerNum, tTrapText}
	STATUS	current
	DESCRIPTION	"Protection Sensor Fail - VRT Um3 LVRT2 - alarm activated"
::= { notifications 293605844 }

tVRTUm3LVRT2SFDisappeared	NOTIFICATION-TYPE
	OBJECTS	{tControllerName, tSerNum, tTrapText}
	STATUS	current
	DESCRIPTION	"Protection Sensor Fail - VRT Um3 LVRT2 - alarm disappeared"
::= { notifications 293605845 }

tVRTUm3LVRT2SFAlarmReset	NOTIFICATION-TYPE
	OBJECTS	{tControllerName, tSerNum, tTrapText}
	STATUS	current
	DESCRIPTION	"Protection Sensor Fail - VRT Um3 LVRT2 - alarm reset"
::= { notifications 293605846 }

tVRTUm3LVRT3L1Activated	NOTIFICATION-TYPE
	OBJECTS	{tControllerName, tSerNum, tTrapText}
	STATUS	current
	DESCRIPTION	"Protection 1. level - VRT Um3 LVRT3 - alarm activated"
::= { notifications 25170392 }

tVRTUm3LVRT3L1Disappeared	NOTIFICATION-TYPE
	OBJECTS	{tControllerName, tSerNum, tTrapText}
	STATUS	current
	DESCRIPTION	"Protection 1. level - VRT Um3 LVRT3 - alarm disappeared"
::= { notifications 25170393 }

tVRTUm3LVRT3L1AlarmReset	NOTIFICATION-TYPE
	OBJECTS	{tControllerName, tSerNum, tTrapText}
	STATUS	current
	DESCRIPTION	"Protection 1. level - VRT Um3 LVRT3 - alarm reset"
::= { notifications 25170394 }

tVRTUm3LVRT3L2Activated	NOTIFICATION-TYPE
	OBJECTS	{tControllerName, tSerNum, tTrapText}
	STATUS	current
	DESCRIPTION	"Protection 2. level - VRT Um3 LVRT3 - alarm activated"
::= { notifications 159388120 }

tVRTUm3LVRT3L2Disappeared	NOTIFICATION-TYPE
	OBJECTS	{tControllerName, tSerNum, tTrapText}
	STATUS	current
	DESCRIPTION	"Protection 2. level - VRT Um3 LVRT3 - alarm disappeared"
::= { notifications 159388121 }

tVRTUm3LVRT3L2AlarmReset	NOTIFICATION-TYPE
	OBJECTS	{tControllerName, tSerNum, tTrapText}
	STATUS	current
	DESCRIPTION	"Protection 2. level - VRT Um3 LVRT3 - alarm reset"
::= { notifications 159388122 }

tVRTUm3LVRT3SFActivated	NOTIFICATION-TYPE
	OBJECTS	{tControllerName, tSerNum, tTrapText}
	STATUS	current
	DESCRIPTION	"Protection Sensor Fail - VRT Um3 LVRT3 - alarm activated"
::= { notifications 293605848 }

tVRTUm3LVRT3SFDisappeared	NOTIFICATION-TYPE
	OBJECTS	{tControllerName, tSerNum, tTrapText}
	STATUS	current
	DESCRIPTION	"Protection Sensor Fail - VRT Um3 LVRT3 - alarm disappeared"
::= { notifications 293605849 }

tVRTUm3LVRT3SFAlarmReset	NOTIFICATION-TYPE
	OBJECTS	{tControllerName, tSerNum, tTrapText}
	STATUS	current
	DESCRIPTION	"Protection Sensor Fail - VRT Um3 LVRT3 - alarm reset"
::= { notifications 293605850 }

tVRTUm12OVRTL1Activated	NOTIFICATION-TYPE
	OBJECTS	{tControllerName, tSerNum, tTrapText}
	STATUS	current
	DESCRIPTION	"Protection 1. level - VRT Um12 OVRT - alarm activated"
::= { notifications 25170284 }

tVRTUm12OVRTL1Disappeared	NOTIFICATION-TYPE
	OBJECTS	{tControllerName, tSerNum, tTrapText}
	STATUS	current
	DESCRIPTION	"Protection 1. level - VRT Um12 OVRT - alarm disappeared"
::= { notifications 25170285 }

tVRTUm12OVRTL1AlarmReset	NOTIFICATION-TYPE
	OBJECTS	{tControllerName, tSerNum, tTrapText}
	STATUS	current
	DESCRIPTION	"Protection 1. level - VRT Um12 OVRT - alarm reset"
::= { notifications 25170286 }

tVRTUm12OVRTL2Activated	NOTIFICATION-TYPE
	OBJECTS	{tControllerName, tSerNum, tTrapText}
	STATUS	current
	DESCRIPTION	"Protection 2. level - VRT Um12 OVRT - alarm activated"
::= { notifications 159388012 }

tVRTUm12OVRTL2Disappeared	NOTIFICATION-TYPE
	OBJECTS	{tControllerName, tSerNum, tTrapText}
	STATUS	current
	DESCRIPTION	"Protection 2. level - VRT Um12 OVRT - alarm disappeared"
::= { notifications 159388013 }

tVRTUm12OVRTL2AlarmReset	NOTIFICATION-TYPE
	OBJECTS	{tControllerName, tSerNum, tTrapText}
	STATUS	current
	DESCRIPTION	"Protection 2. level - VRT Um12 OVRT - alarm reset"
::= { notifications 159388014 }

tVRTUm12OVRTSFActivated	NOTIFICATION-TYPE
	OBJECTS	{tControllerName, tSerNum, tTrapText}
	STATUS	current
	DESCRIPTION	"Protection Sensor Fail - VRT Um12 OVRT - alarm activated"
::= { notifications 293605740 }

tVRTUm12OVRTSFDisappeared	NOTIFICATION-TYPE
	OBJECTS	{tControllerName, tSerNum, tTrapText}
	STATUS	current
	DESCRIPTION	"Protection Sensor Fail - VRT Um12 OVRT - alarm disappeared"
::= { notifications 293605741 }

tVRTUm12OVRTSFAlarmReset	NOTIFICATION-TYPE
	OBJECTS	{tControllerName, tSerNum, tTrapText}
	STATUS	current
	DESCRIPTION	"Protection Sensor Fail - VRT Um12 OVRT - alarm reset"
::= { notifications 293605742 }

tVRTUm12LVRT1L1Activated	NOTIFICATION-TYPE
	OBJECTS	{tControllerName, tSerNum, tTrapText}
	STATUS	current
	DESCRIPTION	"Protection 1. level - VRT Um12 LVRT1 - alarm activated"
::= { notifications 25170336 }

tVRTUm12LVRT1L1Disappeared	NOTIFICATION-TYPE
	OBJECTS	{tControllerName, tSerNum, tTrapText}
	STATUS	current
	DESCRIPTION	"Protection 1. level - VRT Um12 LVRT1 - alarm disappeared"
::= { notifications 25170337 }

tVRTUm12LVRT1L1AlarmReset	NOTIFICATION-TYPE
	OBJECTS	{tControllerName, tSerNum, tTrapText}
	STATUS	current
	DESCRIPTION	"Protection 1. level - VRT Um12 LVRT1 - alarm reset"
::= { notifications 25170338 }

tVRTUm12LVRT1L2Activated	NOTIFICATION-TYPE
	OBJECTS	{tControllerName, tSerNum, tTrapText}
	STATUS	current
	DESCRIPTION	"Protection 2. level - VRT Um12 LVRT1 - alarm activated"
::= { notifications 159388064 }

tVRTUm12LVRT1L2Disappeared	NOTIFICATION-TYPE
	OBJECTS	{tControllerName, tSerNum, tTrapText}
	STATUS	current
	DESCRIPTION	"Protection 2. level - VRT Um12 LVRT1 - alarm disappeared"
::= { notifications 159388065 }

tVRTUm12LVRT1L2AlarmReset	NOTIFICATION-TYPE
	OBJECTS	{tControllerName, tSerNum, tTrapText}
	STATUS	current
	DESCRIPTION	"Protection 2. level - VRT Um12 LVRT1 - alarm reset"
::= { notifications 159388066 }

tVRTUm12LVRT1SFActivated	NOTIFICATION-TYPE
	OBJECTS	{tControllerName, tSerNum, tTrapText}
	STATUS	current
	DESCRIPTION	"Protection Sensor Fail - VRT Um12 LVRT1 - alarm activated"
::= { notifications 293605792 }

tVRTUm12LVRT1SFDisappeared	NOTIFICATION-TYPE
	OBJECTS	{tControllerName, tSerNum, tTrapText}
	STATUS	current
	DESCRIPTION	"Protection Sensor Fail - VRT Um12 LVRT1 - alarm disappeared"
::= { notifications 293605793 }

tVRTUm12LVRT1SFAlarmReset	NOTIFICATION-TYPE
	OBJECTS	{tControllerName, tSerNum, tTrapText}
	STATUS	current
	DESCRIPTION	"Protection Sensor Fail - VRT Um12 LVRT1 - alarm reset"
::= { notifications 293605794 }

tVRTUm12LVRT2L1Activated	NOTIFICATION-TYPE
	OBJECTS	{tControllerName, tSerNum, tTrapText}
	STATUS	current
	DESCRIPTION	"Protection 1. level - VRT Um12 LVRT2 - alarm activated"
::= { notifications 25170288 }

tVRTUm12LVRT2L1Disappeared	NOTIFICATION-TYPE
	OBJECTS	{tControllerName, tSerNum, tTrapText}
	STATUS	current
	DESCRIPTION	"Protection 1. level - VRT Um12 LVRT2 - alarm disappeared"
::= { notifications 25170289 }

tVRTUm12LVRT2L1AlarmReset	NOTIFICATION-TYPE
	OBJECTS	{tControllerName, tSerNum, tTrapText}
	STATUS	current
	DESCRIPTION	"Protection 1. level - VRT Um12 LVRT2 - alarm reset"
::= { notifications 25170290 }

tVRTUm12LVRT2L2Activated	NOTIFICATION-TYPE
	OBJECTS	{tControllerName, tSerNum, tTrapText}
	STATUS	current
	DESCRIPTION	"Protection 2. level - VRT Um12 LVRT2 - alarm activated"
::= { notifications 159388016 }

tVRTUm12LVRT2L2Disappeared	NOTIFICATION-TYPE
	OBJECTS	{tControllerName, tSerNum, tTrapText}
	STATUS	current
	DESCRIPTION	"Protection 2. level - VRT Um12 LVRT2 - alarm disappeared"
::= { notifications 159388017 }

tVRTUm12LVRT2L2AlarmReset	NOTIFICATION-TYPE
	OBJECTS	{tControllerName, tSerNum, tTrapText}
	STATUS	current
	DESCRIPTION	"Protection 2. level - VRT Um12 LVRT2 - alarm reset"
::= { notifications 159388018 }

tVRTUm12LVRT2SFActivated	NOTIFICATION-TYPE
	OBJECTS	{tControllerName, tSerNum, tTrapText}
	STATUS	current
	DESCRIPTION	"Protection Sensor Fail - VRT Um12 LVRT2 - alarm activated"
::= { notifications 293605744 }

tVRTUm12LVRT2SFDisappeared	NOTIFICATION-TYPE
	OBJECTS	{tControllerName, tSerNum, tTrapText}
	STATUS	current
	DESCRIPTION	"Protection Sensor Fail - VRT Um12 LVRT2 - alarm disappeared"
::= { notifications 293605745 }

tVRTUm12LVRT2SFAlarmReset	NOTIFICATION-TYPE
	OBJECTS	{tControllerName, tSerNum, tTrapText}
	STATUS	current
	DESCRIPTION	"Protection Sensor Fail - VRT Um12 LVRT2 - alarm reset"
::= { notifications 293605746 }

tVRTUm12LVRT3L1Activated	NOTIFICATION-TYPE
	OBJECTS	{tControllerName, tSerNum, tTrapText}
	STATUS	current
	DESCRIPTION	"Protection 1. level - VRT Um12 LVRT3 - alarm activated"
::= { notifications 25170292 }

tVRTUm12LVRT3L1Disappeared	NOTIFICATION-TYPE
	OBJECTS	{tControllerName, tSerNum, tTrapText}
	STATUS	current
	DESCRIPTION	"Protection 1. level - VRT Um12 LVRT3 - alarm disappeared"
::= { notifications 25170293 }

tVRTUm12LVRT3L1AlarmReset	NOTIFICATION-TYPE
	OBJECTS	{tControllerName, tSerNum, tTrapText}
	STATUS	current
	DESCRIPTION	"Protection 1. level - VRT Um12 LVRT3 - alarm reset"
::= { notifications 25170294 }

tVRTUm12LVRT3L2Activated	NOTIFICATION-TYPE
	OBJECTS	{tControllerName, tSerNum, tTrapText}
	STATUS	current
	DESCRIPTION	"Protection 2. level - VRT Um12 LVRT3 - alarm activated"
::= { notifications 159388020 }

tVRTUm12LVRT3L2Disappeared	NOTIFICATION-TYPE
	OBJECTS	{tControllerName, tSerNum, tTrapText}
	STATUS	current
	DESCRIPTION	"Protection 2. level - VRT Um12 LVRT3 - alarm disappeared"
::= { notifications 159388021 }

tVRTUm12LVRT3L2AlarmReset	NOTIFICATION-TYPE
	OBJECTS	{tControllerName, tSerNum, tTrapText}
	STATUS	current
	DESCRIPTION	"Protection 2. level - VRT Um12 LVRT3 - alarm reset"
::= { notifications 159388022 }

tVRTUm12LVRT3SFActivated	NOTIFICATION-TYPE
	OBJECTS	{tControllerName, tSerNum, tTrapText}
	STATUS	current
	DESCRIPTION	"Protection Sensor Fail - VRT Um12 LVRT3 - alarm activated"
::= { notifications 293605748 }

tVRTUm12LVRT3SFDisappeared	NOTIFICATION-TYPE
	OBJECTS	{tControllerName, tSerNum, tTrapText}
	STATUS	current
	DESCRIPTION	"Protection Sensor Fail - VRT Um12 LVRT3 - alarm disappeared"
::= { notifications 293605749 }

tVRTUm12LVRT3SFAlarmReset	NOTIFICATION-TYPE
	OBJECTS	{tControllerName, tSerNum, tTrapText}
	STATUS	current
	DESCRIPTION	"Protection Sensor Fail - VRT Um12 LVRT3 - alarm reset"
::= { notifications 293605750 }

tVRTUm23OVRTL1Activated	NOTIFICATION-TYPE
	OBJECTS	{tControllerName, tSerNum, tTrapText}
	STATUS	current
	DESCRIPTION	"Protection 1. level - VRT Um23 OVRT - alarm activated"
::= { notifications 25170296 }

tVRTUm23OVRTL1Disappeared	NOTIFICATION-TYPE
	OBJECTS	{tControllerName, tSerNum, tTrapText}
	STATUS	current
	DESCRIPTION	"Protection 1. level - VRT Um23 OVRT - alarm disappeared"
::= { notifications 25170297 }

tVRTUm23OVRTL1AlarmReset	NOTIFICATION-TYPE
	OBJECTS	{tControllerName, tSerNum, tTrapText}
	STATUS	current
	DESCRIPTION	"Protection 1. level - VRT Um23 OVRT - alarm reset"
::= { notifications 25170298 }

tVRTUm23OVRTL2Activated	NOTIFICATION-TYPE
	OBJECTS	{tControllerName, tSerNum, tTrapText}
	STATUS	current
	DESCRIPTION	"Protection 2. level - VRT Um23 OVRT - alarm activated"
::= { notifications 159388024 }

tVRTUm23OVRTL2Disappeared	NOTIFICATION-TYPE
	OBJECTS	{tControllerName, tSerNum, tTrapText}
	STATUS	current
	DESCRIPTION	"Protection 2. level - VRT Um23 OVRT - alarm disappeared"
::= { notifications 159388025 }

tVRTUm23OVRTL2AlarmReset	NOTIFICATION-TYPE
	OBJECTS	{tControllerName, tSerNum, tTrapText}
	STATUS	current
	DESCRIPTION	"Protection 2. level - VRT Um23 OVRT - alarm reset"
::= { notifications 159388026 }

tVRTUm23OVRTSFActivated	NOTIFICATION-TYPE
	OBJECTS	{tControllerName, tSerNum, tTrapText}
	STATUS	current
	DESCRIPTION	"Protection Sensor Fail - VRT Um23 OVRT - alarm activated"
::= { notifications 293605752 }

tVRTUm23OVRTSFDisappeared	NOTIFICATION-TYPE
	OBJECTS	{tControllerName, tSerNum, tTrapText}
	STATUS	current
	DESCRIPTION	"Protection Sensor Fail - VRT Um23 OVRT - alarm disappeared"
::= { notifications 293605753 }

tVRTUm23OVRTSFAlarmReset	NOTIFICATION-TYPE
	OBJECTS	{tControllerName, tSerNum, tTrapText}
	STATUS	current
	DESCRIPTION	"Protection Sensor Fail - VRT Um23 OVRT - alarm reset"
::= { notifications 293605754 }

tVRTUm23LVRT1L1Activated	NOTIFICATION-TYPE
	OBJECTS	{tControllerName, tSerNum, tTrapText}
	STATUS	current
	DESCRIPTION	"Protection 1. level - VRT Um23 LVRT1 - alarm activated"
::= { notifications 25170340 }

tVRTUm23LVRT1L1Disappeared	NOTIFICATION-TYPE
	OBJECTS	{tControllerName, tSerNum, tTrapText}
	STATUS	current
	DESCRIPTION	"Protection 1. level - VRT Um23 LVRT1 - alarm disappeared"
::= { notifications 25170341 }

tVRTUm23LVRT1L1AlarmReset	NOTIFICATION-TYPE
	OBJECTS	{tControllerName, tSerNum, tTrapText}
	STATUS	current
	DESCRIPTION	"Protection 1. level - VRT Um23 LVRT1 - alarm reset"
::= { notifications 25170342 }

tVRTUm23LVRT1L2Activated	NOTIFICATION-TYPE
	OBJECTS	{tControllerName, tSerNum, tTrapText}
	STATUS	current
	DESCRIPTION	"Protection 2. level - VRT Um23 LVRT1 - alarm activated"
::= { notifications 159388068 }

tVRTUm23LVRT1L2Disappeared	NOTIFICATION-TYPE
	OBJECTS	{tControllerName, tSerNum, tTrapText}
	STATUS	current
	DESCRIPTION	"Protection 2. level - VRT Um23 LVRT1 - alarm disappeared"
::= { notifications 159388069 }

tVRTUm23LVRT1L2AlarmReset	NOTIFICATION-TYPE
	OBJECTS	{tControllerName, tSerNum, tTrapText}
	STATUS	current
	DESCRIPTION	"Protection 2. level - VRT Um23 LVRT1 - alarm reset"
::= { notifications 159388070 }

tVRTUm23LVRT1SFActivated	NOTIFICATION-TYPE
	OBJECTS	{tControllerName, tSerNum, tTrapText}
	STATUS	current
	DESCRIPTION	"Protection Sensor Fail - VRT Um23 LVRT1 - alarm activated"
::= { notifications 293605796 }

tVRTUm23LVRT1SFDisappeared	NOTIFICATION-TYPE
	OBJECTS	{tControllerName, tSerNum, tTrapText}
	STATUS	current
	DESCRIPTION	"Protection Sensor Fail - VRT Um23 LVRT1 - alarm disappeared"
::= { notifications 293605797 }

tVRTUm23LVRT1SFAlarmReset	NOTIFICATION-TYPE
	OBJECTS	{tControllerName, tSerNum, tTrapText}
	STATUS	current
	DESCRIPTION	"Protection Sensor Fail - VRT Um23 LVRT1 - alarm reset"
::= { notifications 293605798 }

tVRTUm23LVRT2L1Activated	NOTIFICATION-TYPE
	OBJECTS	{tControllerName, tSerNum, tTrapText}
	STATUS	current
	DESCRIPTION	"Protection 1. level - VRT Um23 LVRT2 - alarm activated"
::= { notifications 25170300 }

tVRTUm23LVRT2L1Disappeared	NOTIFICATION-TYPE
	OBJECTS	{tControllerName, tSerNum, tTrapText}
	STATUS	current
	DESCRIPTION	"Protection 1. level - VRT Um23 LVRT2 - alarm disappeared"
::= { notifications 25170301 }

tVRTUm23LVRT2L1AlarmReset	NOTIFICATION-TYPE
	OBJECTS	{tControllerName, tSerNum, tTrapText}
	STATUS	current
	DESCRIPTION	"Protection 1. level - VRT Um23 LVRT2 - alarm reset"
::= { notifications 25170302 }

tVRTUm23LVRT2L2Activated	NOTIFICATION-TYPE
	OBJECTS	{tControllerName, tSerNum, tTrapText}
	STATUS	current
	DESCRIPTION	"Protection 2. level - VRT Um23 LVRT2 - alarm activated"
::= { notifications 159388028 }

tVRTUm23LVRT2L2Disappeared	NOTIFICATION-TYPE
	OBJECTS	{tControllerName, tSerNum, tTrapText}
	STATUS	current
	DESCRIPTION	"Protection 2. level - VRT Um23 LVRT2 - alarm disappeared"
::= { notifications 159388029 }

tVRTUm23LVRT2L2AlarmReset	NOTIFICATION-TYPE
	OBJECTS	{tControllerName, tSerNum, tTrapText}
	STATUS	current
	DESCRIPTION	"Protection 2. level - VRT Um23 LVRT2 - alarm reset"
::= { notifications 159388030 }

tVRTUm23LVRT2SFActivated	NOTIFICATION-TYPE
	OBJECTS	{tControllerName, tSerNum, tTrapText}
	STATUS	current
	DESCRIPTION	"Protection Sensor Fail - VRT Um23 LVRT2 - alarm activated"
::= { notifications 293605756 }

tVRTUm23LVRT2SFDisappeared	NOTIFICATION-TYPE
	OBJECTS	{tControllerName, tSerNum, tTrapText}
	STATUS	current
	DESCRIPTION	"Protection Sensor Fail - VRT Um23 LVRT2 - alarm disappeared"
::= { notifications 293605757 }

tVRTUm23LVRT2SFAlarmReset	NOTIFICATION-TYPE
	OBJECTS	{tControllerName, tSerNum, tTrapText}
	STATUS	current
	DESCRIPTION	"Protection Sensor Fail - VRT Um23 LVRT2 - alarm reset"
::= { notifications 293605758 }

tVRTUm23LVRT3L1Activated	NOTIFICATION-TYPE
	OBJECTS	{tControllerName, tSerNum, tTrapText}
	STATUS	current
	DESCRIPTION	"Protection 1. level - VRT Um23 LVRT3 - alarm activated"
::= { notifications 25170304 }

tVRTUm23LVRT3L1Disappeared	NOTIFICATION-TYPE
	OBJECTS	{tControllerName, tSerNum, tTrapText}
	STATUS	current
	DESCRIPTION	"Protection 1. level - VRT Um23 LVRT3 - alarm disappeared"
::= { notifications 25170305 }

tVRTUm23LVRT3L1AlarmReset	NOTIFICATION-TYPE
	OBJECTS	{tControllerName, tSerNum, tTrapText}
	STATUS	current
	DESCRIPTION	"Protection 1. level - VRT Um23 LVRT3 - alarm reset"
::= { notifications 25170306 }

tVRTUm23LVRT3L2Activated	NOTIFICATION-TYPE
	OBJECTS	{tControllerName, tSerNum, tTrapText}
	STATUS	current
	DESCRIPTION	"Protection 2. level - VRT Um23 LVRT3 - alarm activated"
::= { notifications 159388032 }

tVRTUm23LVRT3L2Disappeared	NOTIFICATION-TYPE
	OBJECTS	{tControllerName, tSerNum, tTrapText}
	STATUS	current
	DESCRIPTION	"Protection 2. level - VRT Um23 LVRT3 - alarm disappeared"
::= { notifications 159388033 }

tVRTUm23LVRT3L2AlarmReset	NOTIFICATION-TYPE
	OBJECTS	{tControllerName, tSerNum, tTrapText}
	STATUS	current
	DESCRIPTION	"Protection 2. level - VRT Um23 LVRT3 - alarm reset"
::= { notifications 159388034 }

tVRTUm23LVRT3SFActivated	NOTIFICATION-TYPE
	OBJECTS	{tControllerName, tSerNum, tTrapText}
	STATUS	current
	DESCRIPTION	"Protection Sensor Fail - VRT Um23 LVRT3 - alarm activated"
::= { notifications 293605760 }

tVRTUm23LVRT3SFDisappeared	NOTIFICATION-TYPE
	OBJECTS	{tControllerName, tSerNum, tTrapText}
	STATUS	current
	DESCRIPTION	"Protection Sensor Fail - VRT Um23 LVRT3 - alarm disappeared"
::= { notifications 293605761 }

tVRTUm23LVRT3SFAlarmReset	NOTIFICATION-TYPE
	OBJECTS	{tControllerName, tSerNum, tTrapText}
	STATUS	current
	DESCRIPTION	"Protection Sensor Fail - VRT Um23 LVRT3 - alarm reset"
::= { notifications 293605762 }

tVRTUm31OVRTL1Activated	NOTIFICATION-TYPE
	OBJECTS	{tControllerName, tSerNum, tTrapText}
	STATUS	current
	DESCRIPTION	"Protection 1. level - VRT Um31 OVRT - alarm activated"
::= { notifications 25170308 }

tVRTUm31OVRTL1Disappeared	NOTIFICATION-TYPE
	OBJECTS	{tControllerName, tSerNum, tTrapText}
	STATUS	current
	DESCRIPTION	"Protection 1. level - VRT Um31 OVRT - alarm disappeared"
::= { notifications 25170309 }

tVRTUm31OVRTL1AlarmReset	NOTIFICATION-TYPE
	OBJECTS	{tControllerName, tSerNum, tTrapText}
	STATUS	current
	DESCRIPTION	"Protection 1. level - VRT Um31 OVRT - alarm reset"
::= { notifications 25170310 }

tVRTUm31OVRTL2Activated	NOTIFICATION-TYPE
	OBJECTS	{tControllerName, tSerNum, tTrapText}
	STATUS	current
	DESCRIPTION	"Protection 2. level - VRT Um31 OVRT - alarm activated"
::= { notifications 159388036 }

tVRTUm31OVRTL2Disappeared	NOTIFICATION-TYPE
	OBJECTS	{tControllerName, tSerNum, tTrapText}
	STATUS	current
	DESCRIPTION	"Protection 2. level - VRT Um31 OVRT - alarm disappeared"
::= { notifications 159388037 }

tVRTUm31OVRTL2AlarmReset	NOTIFICATION-TYPE
	OBJECTS	{tControllerName, tSerNum, tTrapText}
	STATUS	current
	DESCRIPTION	"Protection 2. level - VRT Um31 OVRT - alarm reset"
::= { notifications 159388038 }

tVRTUm31OVRTSFActivated	NOTIFICATION-TYPE
	OBJECTS	{tControllerName, tSerNum, tTrapText}
	STATUS	current
	DESCRIPTION	"Protection Sensor Fail - VRT Um31 OVRT - alarm activated"
::= { notifications 293605764 }

tVRTUm31OVRTSFDisappeared	NOTIFICATION-TYPE
	OBJECTS	{tControllerName, tSerNum, tTrapText}
	STATUS	current
	DESCRIPTION	"Protection Sensor Fail - VRT Um31 OVRT - alarm disappeared"
::= { notifications 293605765 }

tVRTUm31OVRTSFAlarmReset	NOTIFICATION-TYPE
	OBJECTS	{tControllerName, tSerNum, tTrapText}
	STATUS	current
	DESCRIPTION	"Protection Sensor Fail - VRT Um31 OVRT - alarm reset"
::= { notifications 293605766 }

tVRTUm31LVRT1L1Activated	NOTIFICATION-TYPE
	OBJECTS	{tControllerName, tSerNum, tTrapText}
	STATUS	current
	DESCRIPTION	"Protection 1. level - VRT Um31 LVRT1 - alarm activated"
::= { notifications 25170344 }

tVRTUm31LVRT1L1Disappeared	NOTIFICATION-TYPE
	OBJECTS	{tControllerName, tSerNum, tTrapText}
	STATUS	current
	DESCRIPTION	"Protection 1. level - VRT Um31 LVRT1 - alarm disappeared"
::= { notifications 25170345 }

tVRTUm31LVRT1L1AlarmReset	NOTIFICATION-TYPE
	OBJECTS	{tControllerName, tSerNum, tTrapText}
	STATUS	current
	DESCRIPTION	"Protection 1. level - VRT Um31 LVRT1 - alarm reset"
::= { notifications 25170346 }

tVRTUm31LVRT1L2Activated	NOTIFICATION-TYPE
	OBJECTS	{tControllerName, tSerNum, tTrapText}
	STATUS	current
	DESCRIPTION	"Protection 2. level - VRT Um31 LVRT1 - alarm activated"
::= { notifications 159388072 }

tVRTUm31LVRT1L2Disappeared	NOTIFICATION-TYPE
	OBJECTS	{tControllerName, tSerNum, tTrapText}
	STATUS	current
	DESCRIPTION	"Protection 2. level - VRT Um31 LVRT1 - alarm disappeared"
::= { notifications 159388073 }

tVRTUm31LVRT1L2AlarmReset	NOTIFICATION-TYPE
	OBJECTS	{tControllerName, tSerNum, tTrapText}
	STATUS	current
	DESCRIPTION	"Protection 2. level - VRT Um31 LVRT1 - alarm reset"
::= { notifications 159388074 }

tVRTUm31LVRT1SFActivated	NOTIFICATION-TYPE
	OBJECTS	{tControllerName, tSerNum, tTrapText}
	STATUS	current
	DESCRIPTION	"Protection Sensor Fail - VRT Um31 LVRT1 - alarm activated"
::= { notifications 293605800 }

tVRTUm31LVRT1SFDisappeared	NOTIFICATION-TYPE
	OBJECTS	{tControllerName, tSerNum, tTrapText}
	STATUS	current
	DESCRIPTION	"Protection Sensor Fail - VRT Um31 LVRT1 - alarm disappeared"
::= { notifications 293605801 }

tVRTUm31LVRT1SFAlarmReset	NOTIFICATION-TYPE
	OBJECTS	{tControllerName, tSerNum, tTrapText}
	STATUS	current
	DESCRIPTION	"Protection Sensor Fail - VRT Um31 LVRT1 - alarm reset"
::= { notifications 293605802 }

tVRTUm31LVRT2L1Activated	NOTIFICATION-TYPE
	OBJECTS	{tControllerName, tSerNum, tTrapText}
	STATUS	current
	DESCRIPTION	"Protection 1. level - VRT Um31 LVRT2 - alarm activated"
::= { notifications 25170312 }

tVRTUm31LVRT2L1Disappeared	NOTIFICATION-TYPE
	OBJECTS	{tControllerName, tSerNum, tTrapText}
	STATUS	current
	DESCRIPTION	"Protection 1. level - VRT Um31 LVRT2 - alarm disappeared"
::= { notifications 25170313 }

tVRTUm31LVRT2L1AlarmReset	NOTIFICATION-TYPE
	OBJECTS	{tControllerName, tSerNum, tTrapText}
	STATUS	current
	DESCRIPTION	"Protection 1. level - VRT Um31 LVRT2 - alarm reset"
::= { notifications 25170314 }

tVRTUm31LVRT2L2Activated	NOTIFICATION-TYPE
	OBJECTS	{tControllerName, tSerNum, tTrapText}
	STATUS	current
	DESCRIPTION	"Protection 2. level - VRT Um31 LVRT2 - alarm activated"
::= { notifications 159388040 }

tVRTUm31LVRT2L2Disappeared	NOTIFICATION-TYPE
	OBJECTS	{tControllerName, tSerNum, tTrapText}
	STATUS	current
	DESCRIPTION	"Protection 2. level - VRT Um31 LVRT2 - alarm disappeared"
::= { notifications 159388041 }

tVRTUm31LVRT2L2AlarmReset	NOTIFICATION-TYPE
	OBJECTS	{tControllerName, tSerNum, tTrapText}
	STATUS	current
	DESCRIPTION	"Protection 2. level - VRT Um31 LVRT2 - alarm reset"
::= { notifications 159388042 }

tVRTUm31LVRT2SFActivated	NOTIFICATION-TYPE
	OBJECTS	{tControllerName, tSerNum, tTrapText}
	STATUS	current
	DESCRIPTION	"Protection Sensor Fail - VRT Um31 LVRT2 - alarm activated"
::= { notifications 293605768 }

tVRTUm31LVRT2SFDisappeared	NOTIFICATION-TYPE
	OBJECTS	{tControllerName, tSerNum, tTrapText}
	STATUS	current
	DESCRIPTION	"Protection Sensor Fail - VRT Um31 LVRT2 - alarm disappeared"
::= { notifications 293605769 }

tVRTUm31LVRT2SFAlarmReset	NOTIFICATION-TYPE
	OBJECTS	{tControllerName, tSerNum, tTrapText}
	STATUS	current
	DESCRIPTION	"Protection Sensor Fail - VRT Um31 LVRT2 - alarm reset"
::= { notifications 293605770 }

tVRTUm31LVRT3L1Activated	NOTIFICATION-TYPE
	OBJECTS	{tControllerName, tSerNum, tTrapText}
	STATUS	current
	DESCRIPTION	"Protection 1. level - VRT Um31 LVRT3 - alarm activated"
::= { notifications 25170316 }

tVRTUm31LVRT3L1Disappeared	NOTIFICATION-TYPE
	OBJECTS	{tControllerName, tSerNum, tTrapText}
	STATUS	current
	DESCRIPTION	"Protection 1. level - VRT Um31 LVRT3 - alarm disappeared"
::= { notifications 25170317 }

tVRTUm31LVRT3L1AlarmReset	NOTIFICATION-TYPE
	OBJECTS	{tControllerName, tSerNum, tTrapText}
	STATUS	current
	DESCRIPTION	"Protection 1. level - VRT Um31 LVRT3 - alarm reset"
::= { notifications 25170318 }

tVRTUm31LVRT3L2Activated	NOTIFICATION-TYPE
	OBJECTS	{tControllerName, tSerNum, tTrapText}
	STATUS	current
	DESCRIPTION	"Protection 2. level - VRT Um31 LVRT3 - alarm activated"
::= { notifications 159388044 }

tVRTUm31LVRT3L2Disappeared	NOTIFICATION-TYPE
	OBJECTS	{tControllerName, tSerNum, tTrapText}
	STATUS	current
	DESCRIPTION	"Protection 2. level - VRT Um31 LVRT3 - alarm disappeared"
::= { notifications 159388045 }

tVRTUm31LVRT3L2AlarmReset	NOTIFICATION-TYPE
	OBJECTS	{tControllerName, tSerNum, tTrapText}
	STATUS	current
	DESCRIPTION	"Protection 2. level - VRT Um31 LVRT3 - alarm reset"
::= { notifications 159388046 }

tVRTUm31LVRT3SFActivated	NOTIFICATION-TYPE
	OBJECTS	{tControllerName, tSerNum, tTrapText}
	STATUS	current
	DESCRIPTION	"Protection Sensor Fail - VRT Um31 LVRT3 - alarm activated"
::= { notifications 293605772 }

tVRTUm31LVRT3SFDisappeared	NOTIFICATION-TYPE
	OBJECTS	{tControllerName, tSerNum, tTrapText}
	STATUS	current
	DESCRIPTION	"Protection Sensor Fail - VRT Um31 LVRT3 - alarm disappeared"
::= { notifications 293605773 }

tVRTUm31LVRT3SFAlarmReset	NOTIFICATION-TYPE
	OBJECTS	{tControllerName, tSerNum, tTrapText}
	STATUS	current
	DESCRIPTION	"Protection Sensor Fail - VRT Um31 LVRT3 - alarm reset"
::= { notifications 293605774 }

tLVRTUm1SevereL1Activated	NOTIFICATION-TYPE
	OBJECTS	{tControllerName, tSerNum, tTrapText}
	STATUS	current
	DESCRIPTION	"Protection 1. level - LVRT Um1 Severe - alarm activated"
::= { notifications 25170412 }

tLVRTUm1SevereL1Disappeared	NOTIFICATION-TYPE
	OBJECTS	{tControllerName, tSerNum, tTrapText}
	STATUS	current
	DESCRIPTION	"Protection 1. level - LVRT Um1 Severe - alarm disappeared"
::= { notifications 25170413 }

tLVRTUm1SevereL1AlarmReset	NOTIFICATION-TYPE
	OBJECTS	{tControllerName, tSerNum, tTrapText}
	STATUS	current
	DESCRIPTION	"Protection 1. level - LVRT Um1 Severe - alarm reset"
::= { notifications 25170414 }

tLVRTUm1SevereL2Activated	NOTIFICATION-TYPE
	OBJECTS	{tControllerName, tSerNum, tTrapText}
	STATUS	current
	DESCRIPTION	"Protection 2. level - LVRT Um1 Severe - alarm activated"
::= { notifications 159388140 }

tLVRTUm1SevereL2Disappeared	NOTIFICATION-TYPE
	OBJECTS	{tControllerName, tSerNum, tTrapText}
	STATUS	current
	DESCRIPTION	"Protection 2. level - LVRT Um1 Severe - alarm disappeared"
::= { notifications 159388141 }

tLVRTUm1SevereL2AlarmReset	NOTIFICATION-TYPE
	OBJECTS	{tControllerName, tSerNum, tTrapText}
	STATUS	current
	DESCRIPTION	"Protection 2. level - LVRT Um1 Severe - alarm reset"
::= { notifications 159388142 }

tLVRTUm1SevereSFActivated	NOTIFICATION-TYPE
	OBJECTS	{tControllerName, tSerNum, tTrapText}
	STATUS	current
	DESCRIPTION	"Protection Sensor Fail - LVRT Um1 Severe - alarm activated"
::= { notifications 293605868 }

tLVRTUm1SevereSFDisappeared	NOTIFICATION-TYPE
	OBJECTS	{tControllerName, tSerNum, tTrapText}
	STATUS	current
	DESCRIPTION	"Protection Sensor Fail - LVRT Um1 Severe - alarm disappeared"
::= { notifications 293605869 }

tLVRTUm1SevereSFAlarmReset	NOTIFICATION-TYPE
	OBJECTS	{tControllerName, tSerNum, tTrapText}
	STATUS	current
	DESCRIPTION	"Protection Sensor Fail - LVRT Um1 Severe - alarm reset"
::= { notifications 293605870 }

tLVRTUm2SevereL1Activated	NOTIFICATION-TYPE
	OBJECTS	{tControllerName, tSerNum, tTrapText}
	STATUS	current
	DESCRIPTION	"Protection 1. level - LVRT Um2 Severe - alarm activated"
::= { notifications 25170416 }

tLVRTUm2SevereL1Disappeared	NOTIFICATION-TYPE
	OBJECTS	{tControllerName, tSerNum, tTrapText}
	STATUS	current
	DESCRIPTION	"Protection 1. level - LVRT Um2 Severe - alarm disappeared"
::= { notifications 25170417 }

tLVRTUm2SevereL1AlarmReset	NOTIFICATION-TYPE
	OBJECTS	{tControllerName, tSerNum, tTrapText}
	STATUS	current
	DESCRIPTION	"Protection 1. level - LVRT Um2 Severe - alarm reset"
::= { notifications 25170418 }

tLVRTUm2SevereL2Activated	NOTIFICATION-TYPE
	OBJECTS	{tControllerName, tSerNum, tTrapText}
	STATUS	current
	DESCRIPTION	"Protection 2. level - LVRT Um2 Severe - alarm activated"
::= { notifications 159388144 }

tLVRTUm2SevereL2Disappeared	NOTIFICATION-TYPE
	OBJECTS	{tControllerName, tSerNum, tTrapText}
	STATUS	current
	DESCRIPTION	"Protection 2. level - LVRT Um2 Severe - alarm disappeared"
::= { notifications 159388145 }

tLVRTUm2SevereL2AlarmReset	NOTIFICATION-TYPE
	OBJECTS	{tControllerName, tSerNum, tTrapText}
	STATUS	current
	DESCRIPTION	"Protection 2. level - LVRT Um2 Severe - alarm reset"
::= { notifications 159388146 }

tLVRTUm2SevereSFActivated	NOTIFICATION-TYPE
	OBJECTS	{tControllerName, tSerNum, tTrapText}
	STATUS	current
	DESCRIPTION	"Protection Sensor Fail - LVRT Um2 Severe - alarm activated"
::= { notifications 293605872 }

tLVRTUm2SevereSFDisappeared	NOTIFICATION-TYPE
	OBJECTS	{tControllerName, tSerNum, tTrapText}
	STATUS	current
	DESCRIPTION	"Protection Sensor Fail - LVRT Um2 Severe - alarm disappeared"
::= { notifications 293605873 }

tLVRTUm2SevereSFAlarmReset	NOTIFICATION-TYPE
	OBJECTS	{tControllerName, tSerNum, tTrapText}
	STATUS	current
	DESCRIPTION	"Protection Sensor Fail - LVRT Um2 Severe - alarm reset"
::= { notifications 293605874 }

tLVRTUm3SevereL1Activated	NOTIFICATION-TYPE
	OBJECTS	{tControllerName, tSerNum, tTrapText}
	STATUS	current
	DESCRIPTION	"Protection 1. level - LVRT Um3 Severe - alarm activated"
::= { notifications 25170420 }

tLVRTUm3SevereL1Disappeared	NOTIFICATION-TYPE
	OBJECTS	{tControllerName, tSerNum, tTrapText}
	STATUS	current
	DESCRIPTION	"Protection 1. level - LVRT Um3 Severe - alarm disappeared"
::= { notifications 25170421 }

tLVRTUm3SevereL1AlarmReset	NOTIFICATION-TYPE
	OBJECTS	{tControllerName, tSerNum, tTrapText}
	STATUS	current
	DESCRIPTION	"Protection 1. level - LVRT Um3 Severe - alarm reset"
::= { notifications 25170422 }

tLVRTUm3SevereL2Activated	NOTIFICATION-TYPE
	OBJECTS	{tControllerName, tSerNum, tTrapText}
	STATUS	current
	DESCRIPTION	"Protection 2. level - LVRT Um3 Severe - alarm activated"
::= { notifications 159388148 }

tLVRTUm3SevereL2Disappeared	NOTIFICATION-TYPE
	OBJECTS	{tControllerName, tSerNum, tTrapText}
	STATUS	current
	DESCRIPTION	"Protection 2. level - LVRT Um3 Severe - alarm disappeared"
::= { notifications 159388149 }

tLVRTUm3SevereL2AlarmReset	NOTIFICATION-TYPE
	OBJECTS	{tControllerName, tSerNum, tTrapText}
	STATUS	current
	DESCRIPTION	"Protection 2. level - LVRT Um3 Severe - alarm reset"
::= { notifications 159388150 }

tLVRTUm3SevereSFActivated	NOTIFICATION-TYPE
	OBJECTS	{tControllerName, tSerNum, tTrapText}
	STATUS	current
	DESCRIPTION	"Protection Sensor Fail - LVRT Um3 Severe - alarm activated"
::= { notifications 293605876 }

tLVRTUm3SevereSFDisappeared	NOTIFICATION-TYPE
	OBJECTS	{tControllerName, tSerNum, tTrapText}
	STATUS	current
	DESCRIPTION	"Protection Sensor Fail - LVRT Um3 Severe - alarm disappeared"
::= { notifications 293605877 }

tLVRTUm3SevereSFAlarmReset	NOTIFICATION-TYPE
	OBJECTS	{tControllerName, tSerNum, tTrapText}
	STATUS	current
	DESCRIPTION	"Protection Sensor Fail - LVRT Um3 Severe - alarm reset"
::= { notifications 293605878 }

tLVRTUm12SevereL1Activated	NOTIFICATION-TYPE
	OBJECTS	{tControllerName, tSerNum, tTrapText}
	STATUS	current
	DESCRIPTION	"Protection 1. level - LVRT Um12 Severe - alarm activated"
::= { notifications 25170424 }

tLVRTUm12SevereL1Disappeared	NOTIFICATION-TYPE
	OBJECTS	{tControllerName, tSerNum, tTrapText}
	STATUS	current
	DESCRIPTION	"Protection 1. level - LVRT Um12 Severe - alarm disappeared"
::= { notifications 25170425 }

tLVRTUm12SevereL1AlarmReset	NOTIFICATION-TYPE
	OBJECTS	{tControllerName, tSerNum, tTrapText}
	STATUS	current
	DESCRIPTION	"Protection 1. level - LVRT Um12 Severe - alarm reset"
::= { notifications 25170426 }

tLVRTUm12SevereL2Activated	NOTIFICATION-TYPE
	OBJECTS	{tControllerName, tSerNum, tTrapText}
	STATUS	current
	DESCRIPTION	"Protection 2. level - LVRT Um12 Severe - alarm activated"
::= { notifications 159388152 }

tLVRTUm12SevereL2Disappeared	NOTIFICATION-TYPE
	OBJECTS	{tControllerName, tSerNum, tTrapText}
	STATUS	current
	DESCRIPTION	"Protection 2. level - LVRT Um12 Severe - alarm disappeared"
::= { notifications 159388153 }

tLVRTUm12SevereL2AlarmReset	NOTIFICATION-TYPE
	OBJECTS	{tControllerName, tSerNum, tTrapText}
	STATUS	current
	DESCRIPTION	"Protection 2. level - LVRT Um12 Severe - alarm reset"
::= { notifications 159388154 }

tLVRTUm12SevereSFActivated	NOTIFICATION-TYPE
	OBJECTS	{tControllerName, tSerNum, tTrapText}
	STATUS	current
	DESCRIPTION	"Protection Sensor Fail - LVRT Um12 Severe - alarm activated"
::= { notifications 293605880 }

tLVRTUm12SevereSFDisappeared	NOTIFICATION-TYPE
	OBJECTS	{tControllerName, tSerNum, tTrapText}
	STATUS	current
	DESCRIPTION	"Protection Sensor Fail - LVRT Um12 Severe - alarm disappeared"
::= { notifications 293605881 }

tLVRTUm12SevereSFAlarmReset	NOTIFICATION-TYPE
	OBJECTS	{tControllerName, tSerNum, tTrapText}
	STATUS	current
	DESCRIPTION	"Protection Sensor Fail - LVRT Um12 Severe - alarm reset"
::= { notifications 293605882 }

tLVRTUm23SevereL1Activated	NOTIFICATION-TYPE
	OBJECTS	{tControllerName, tSerNum, tTrapText}
	STATUS	current
	DESCRIPTION	"Protection 1. level - LVRT Um23 Severe - alarm activated"
::= { notifications 25170428 }

tLVRTUm23SevereL1Disappeared	NOTIFICATION-TYPE
	OBJECTS	{tControllerName, tSerNum, tTrapText}
	STATUS	current
	DESCRIPTION	"Protection 1. level - LVRT Um23 Severe - alarm disappeared"
::= { notifications 25170429 }

tLVRTUm23SevereL1AlarmReset	NOTIFICATION-TYPE
	OBJECTS	{tControllerName, tSerNum, tTrapText}
	STATUS	current
	DESCRIPTION	"Protection 1. level - LVRT Um23 Severe - alarm reset"
::= { notifications 25170430 }

tLVRTUm23SevereL2Activated	NOTIFICATION-TYPE
	OBJECTS	{tControllerName, tSerNum, tTrapText}
	STATUS	current
	DESCRIPTION	"Protection 2. level - LVRT Um23 Severe - alarm activated"
::= { notifications 159388156 }

tLVRTUm23SevereL2Disappeared	NOTIFICATION-TYPE
	OBJECTS	{tControllerName, tSerNum, tTrapText}
	STATUS	current
	DESCRIPTION	"Protection 2. level - LVRT Um23 Severe - alarm disappeared"
::= { notifications 159388157 }

tLVRTUm23SevereL2AlarmReset	NOTIFICATION-TYPE
	OBJECTS	{tControllerName, tSerNum, tTrapText}
	STATUS	current
	DESCRIPTION	"Protection 2. level - LVRT Um23 Severe - alarm reset"
::= { notifications 159388158 }

tLVRTUm23SevereSFActivated	NOTIFICATION-TYPE
	OBJECTS	{tControllerName, tSerNum, tTrapText}
	STATUS	current
	DESCRIPTION	"Protection Sensor Fail - LVRT Um23 Severe - alarm activated"
::= { notifications 293605884 }

tLVRTUm23SevereSFDisappeared	NOTIFICATION-TYPE
	OBJECTS	{tControllerName, tSerNum, tTrapText}
	STATUS	current
	DESCRIPTION	"Protection Sensor Fail - LVRT Um23 Severe - alarm disappeared"
::= { notifications 293605885 }

tLVRTUm23SevereSFAlarmReset	NOTIFICATION-TYPE
	OBJECTS	{tControllerName, tSerNum, tTrapText}
	STATUS	current
	DESCRIPTION	"Protection Sensor Fail - LVRT Um23 Severe - alarm reset"
::= { notifications 293605886 }

tLVRTUm31SevereL1Activated	NOTIFICATION-TYPE
	OBJECTS	{tControllerName, tSerNum, tTrapText}
	STATUS	current
	DESCRIPTION	"Protection 1. level - LVRT Um31 Severe - alarm activated"
::= { notifications 25170432 }

tLVRTUm31SevereL1Disappeared	NOTIFICATION-TYPE
	OBJECTS	{tControllerName, tSerNum, tTrapText}
	STATUS	current
	DESCRIPTION	"Protection 1. level - LVRT Um31 Severe - alarm disappeared"
::= { notifications 25170433 }

tLVRTUm31SevereL1AlarmReset	NOTIFICATION-TYPE
	OBJECTS	{tControllerName, tSerNum, tTrapText}
	STATUS	current
	DESCRIPTION	"Protection 1. level - LVRT Um31 Severe - alarm reset"
::= { notifications 25170434 }

tLVRTUm31SevereL2Activated	NOTIFICATION-TYPE
	OBJECTS	{tControllerName, tSerNum, tTrapText}
	STATUS	current
	DESCRIPTION	"Protection 2. level - LVRT Um31 Severe - alarm activated"
::= { notifications 159388160 }

tLVRTUm31SevereL2Disappeared	NOTIFICATION-TYPE
	OBJECTS	{tControllerName, tSerNum, tTrapText}
	STATUS	current
	DESCRIPTION	"Protection 2. level - LVRT Um31 Severe - alarm disappeared"
::= { notifications 159388161 }

tLVRTUm31SevereL2AlarmReset	NOTIFICATION-TYPE
	OBJECTS	{tControllerName, tSerNum, tTrapText}
	STATUS	current
	DESCRIPTION	"Protection 2. level - LVRT Um31 Severe - alarm reset"
::= { notifications 159388162 }

tLVRTUm31SevereSFActivated	NOTIFICATION-TYPE
	OBJECTS	{tControllerName, tSerNum, tTrapText}
	STATUS	current
	DESCRIPTION	"Protection Sensor Fail - LVRT Um31 Severe - alarm activated"
::= { notifications 293605888 }

tLVRTUm31SevereSFDisappeared	NOTIFICATION-TYPE
	OBJECTS	{tControllerName, tSerNum, tTrapText}
	STATUS	current
	DESCRIPTION	"Protection Sensor Fail - LVRT Um31 Severe - alarm disappeared"
::= { notifications 293605889 }

tLVRTUm31SevereSFAlarmReset	NOTIFICATION-TYPE
	OBJECTS	{tControllerName, tSerNum, tTrapText}
	STATUS	current
	DESCRIPTION	"Protection Sensor Fail - LVRT Um31 Severe - alarm reset"
::= { notifications 293605890 }

tVectorShiftL1Activated	NOTIFICATION-TYPE
	OBJECTS	{tControllerName, tSerNum, tTrapText}
	STATUS	current
	DESCRIPTION	"Protection 1. level - VectorShift - alarm activated"
::= { notifications 25169224 }

tVectorShiftL1Disappeared	NOTIFICATION-TYPE
	OBJECTS	{tControllerName, tSerNum, tTrapText}
	STATUS	current
	DESCRIPTION	"Protection 1. level - VectorShift - alarm disappeared"
::= { notifications 25169225 }

tVectorShiftL1AlarmReset	NOTIFICATION-TYPE
	OBJECTS	{tControllerName, tSerNum, tTrapText}
	STATUS	current
	DESCRIPTION	"Protection 1. level - VectorShift - alarm reset"
::= { notifications 25169226 }

tROCOF1L1Activated	NOTIFICATION-TYPE
	OBJECTS	{tControllerName, tSerNum, tTrapText}
	STATUS	current
	DESCRIPTION	"Protection 1. level - ROCOF 1 - alarm activated"
::= { notifications 25169228 }

tROCOF1L1Disappeared	NOTIFICATION-TYPE
	OBJECTS	{tControllerName, tSerNum, tTrapText}
	STATUS	current
	DESCRIPTION	"Protection 1. level - ROCOF 1 - alarm disappeared"
::= { notifications 25169229 }

tROCOF1L1AlarmReset	NOTIFICATION-TYPE
	OBJECTS	{tControllerName, tSerNum, tTrapText}
	STATUS	current
	DESCRIPTION	"Protection 1. level - ROCOF 1 - alarm reset"
::= { notifications 25169230 }

tROCOF2L1Activated	NOTIFICATION-TYPE
	OBJECTS	{tControllerName, tSerNum, tTrapText}
	STATUS	current
	DESCRIPTION	"Protection 1. level - ROCOF 2 - alarm activated"
::= { notifications 25170272 }

tROCOF2L1Disappeared	NOTIFICATION-TYPE
	OBJECTS	{tControllerName, tSerNum, tTrapText}
	STATUS	current
	DESCRIPTION	"Protection 1. level - ROCOF 2 - alarm disappeared"
::= { notifications 25170273 }

tROCOF2L1AlarmReset	NOTIFICATION-TYPE
	OBJECTS	{tControllerName, tSerNum, tTrapText}
	STATUS	current
	DESCRIPTION	"Protection 1. level - ROCOF 2 - alarm reset"
::= { notifications 25170274 }

tROCOF3L1Activated	NOTIFICATION-TYPE
	OBJECTS	{tControllerName, tSerNum, tTrapText}
	STATUS	current
	DESCRIPTION	"Protection 1. level - ROCOF 3 - alarm activated"
::= { notifications 25170276 }

tROCOF3L1Disappeared	NOTIFICATION-TYPE
	OBJECTS	{tControllerName, tSerNum, tTrapText}
	STATUS	current
	DESCRIPTION	"Protection 1. level - ROCOF 3 - alarm disappeared"
::= { notifications 25170277 }

tROCOF3L1AlarmReset	NOTIFICATION-TYPE
	OBJECTS	{tControllerName, tSerNum, tTrapText}
	STATUS	current
	DESCRIPTION	"Protection 1. level - ROCOF 3 - alarm reset"
::= { notifications 25170278 }

tROCOF4L1Activated	NOTIFICATION-TYPE
	OBJECTS	{tControllerName, tSerNum, tTrapText}
	STATUS	current
	DESCRIPTION	"Protection 1. level - ROCOF 4 - alarm activated"
::= { notifications 25170280 }

tROCOF4L1Disappeared	NOTIFICATION-TYPE
	OBJECTS	{tControllerName, tSerNum, tTrapText}
	STATUS	current
	DESCRIPTION	"Protection 1. level - ROCOF 4 - alarm disappeared"
::= { notifications 25170281 }

tROCOF4L1AlarmReset	NOTIFICATION-TYPE
	OBJECTS	{tControllerName, tSerNum, tTrapText}
	STATUS	current
	DESCRIPTION	"Protection 1. level - ROCOF 4 - alarm reset"
::= { notifications 25170282 }

tBatteryVoltsL1Activated	NOTIFICATION-TYPE
	OBJECTS	{tControllerName, tSerNum, tTrapText}
	STATUS	current
	DESCRIPTION	"Protection 1. level - Battery Volts - alarm activated"
::= { notifications 25168232 }

tBatteryVoltsL1Disappeared	NOTIFICATION-TYPE
	OBJECTS	{tControllerName, tSerNum, tTrapText}
	STATUS	current
	DESCRIPTION	"Protection 1. level - Battery Volts - alarm disappeared"
::= { notifications 25168233 }

tBatteryVoltsL1AlarmReset	NOTIFICATION-TYPE
	OBJECTS	{tControllerName, tSerNum, tTrapText}
	STATUS	current
	DESCRIPTION	"Protection 1. level - Battery Volts - alarm reset"
::= { notifications 25168234 }

tBatteryVoltsL2Activated	NOTIFICATION-TYPE
	OBJECTS	{tControllerName, tSerNum, tTrapText}
	STATUS	current
	DESCRIPTION	"Protection 2. level - Battery Volts - alarm activated"
::= { notifications 159385960 }

tBatteryVoltsL2Disappeared	NOTIFICATION-TYPE
	OBJECTS	{tControllerName, tSerNum, tTrapText}
	STATUS	current
	DESCRIPTION	"Protection 2. level - Battery Volts - alarm disappeared"
::= { notifications 159385961 }

tBatteryVoltsL2AlarmReset	NOTIFICATION-TYPE
	OBJECTS	{tControllerName, tSerNum, tTrapText}
	STATUS	current
	DESCRIPTION	"Protection 2. level - Battery Volts - alarm reset"
::= { notifications 159385962 }

tBatteryVoltsSFActivated	NOTIFICATION-TYPE
	OBJECTS	{tControllerName, tSerNum, tTrapText}
	STATUS	current
	DESCRIPTION	"Protection Sensor Fail - Battery Volts - alarm activated"
::= { notifications 293603688 }

tBatteryVoltsSFDisappeared	NOTIFICATION-TYPE
	OBJECTS	{tControllerName, tSerNum, tTrapText}
	STATUS	current
	DESCRIPTION	"Protection Sensor Fail - Battery Volts - alarm disappeared"
::= { notifications 293603689 }

tBatteryVoltsSFAlarmReset	NOTIFICATION-TYPE
	OBJECTS	{tControllerName, tSerNum, tTrapText}
	STATUS	current
	DESCRIPTION	"Protection Sensor Fail - Battery Volts - alarm reset"
::= { notifications 293603690 }

tSoftTransferFailL1Activated	NOTIFICATION-TYPE
	OBJECTS	{tControllerName, tSerNum, tTrapText}
	STATUS	current
	DESCRIPTION	"Protection 1. level - Soft Transfer Fail - alarm activated"
::= { notifications 25169232 }

tSoftTransferFailL1Disappeared	NOTIFICATION-TYPE
	OBJECTS	{tControllerName, tSerNum, tTrapText}
	STATUS	current
	DESCRIPTION	"Protection 1. level - Soft Transfer Fail - alarm disappeared"
::= { notifications 25169233 }

tSoftTransferFailL1AlarmReset	NOTIFICATION-TYPE
	OBJECTS	{tControllerName, tSerNum, tTrapText}
	STATUS	current
	DESCRIPTION	"Protection 1. level - Soft Transfer Fail - alarm reset"
::= { notifications 25169234 }

tRentalTimerBlockStartL1Activated	NOTIFICATION-TYPE
	OBJECTS	{tControllerName, tSerNum, tTrapText}
	STATUS	current
	DESCRIPTION	"Protection 1. level - Rental Timer Block Start - alarm activated"
::= { notifications 25168936 }

tRentalTimerBlockStartL1Disappeared	NOTIFICATION-TYPE
	OBJECTS	{tControllerName, tSerNum, tTrapText}
	STATUS	current
	DESCRIPTION	"Protection 1. level - Rental Timer Block Start - alarm disappeared"
::= { notifications 25168937 }

tRentalTimerBlockStartL1AlarmReset	NOTIFICATION-TYPE
	OBJECTS	{tControllerName, tSerNum, tTrapText}
	STATUS	current
	DESCRIPTION	"Protection 1. level - Rental Timer Block Start - alarm reset"
::= { notifications 25168938 }

tManualRestoreL1Activated	NOTIFICATION-TYPE
	OBJECTS	{tControllerName, tSerNum, tTrapText}
	STATUS	current
	DESCRIPTION	"Protection 1. level - Manual Restore - alarm activated"
::= { notifications 25168956 }

tManualRestoreL1Disappeared	NOTIFICATION-TYPE
	OBJECTS	{tControllerName, tSerNum, tTrapText}
	STATUS	current
	DESCRIPTION	"Protection 1. level - Manual Restore - alarm disappeared"
::= { notifications 25168957 }

tManualRestoreL1AlarmReset	NOTIFICATION-TYPE
	OBJECTS	{tControllerName, tSerNum, tTrapText}
	STATUS	current
	DESCRIPTION	"Protection 1. level - Manual Restore - alarm reset"
::= { notifications 25168958 }

tWrongPowerFormatL1Activated	NOTIFICATION-TYPE
	OBJECTS	{tControllerName, tSerNum, tTrapText}
	STATUS	current
	DESCRIPTION	"Protection 1. level - Wrong Power Format - alarm activated"
::= { notifications 25166420 }

tWrongPowerFormatL1Disappeared	NOTIFICATION-TYPE
	OBJECTS	{tControllerName, tSerNum, tTrapText}
	STATUS	current
	DESCRIPTION	"Protection 1. level - Wrong Power Format - alarm disappeared"
::= { notifications 25166421 }

tWrongPowerFormatL1AlarmReset	NOTIFICATION-TYPE
	OBJECTS	{tControllerName, tSerNum, tTrapText}
	STATUS	current
	DESCRIPTION	"Protection 1. level - Wrong Power Format - alarm reset"
::= { notifications 25166422 }

tDeadBusGCBBlockedL1Activated	NOTIFICATION-TYPE
	OBJECTS	{tControllerName, tSerNum, tTrapText}
	STATUS	current
	DESCRIPTION	"Protection 1. level - Dead Bus GCB Blocked - alarm activated"
::= { notifications 25167656 }

tDeadBusGCBBlockedL1Disappeared	NOTIFICATION-TYPE
	OBJECTS	{tControllerName, tSerNum, tTrapText}
	STATUS	current
	DESCRIPTION	"Protection 1. level - Dead Bus GCB Blocked - alarm disappeared"
::= { notifications 25167657 }

tDeadBusGCBBlockedL1AlarmReset	NOTIFICATION-TYPE
	OBJECTS	{tControllerName, tSerNum, tTrapText}
	STATUS	current
	DESCRIPTION	"Protection 1. level - Dead Bus GCB Blocked - alarm reset"
::= { notifications 25167658 }

tESTOPL2Activated	NOTIFICATION-TYPE
	OBJECTS	{tControllerName, tSerNum, tTrapText}
	STATUS	current
	DESCRIPTION	"Protection 2. level - E-STOP - alarm activated"
::= { notifications 159386964 }

tESTOPL2Disappeared	NOTIFICATION-TYPE
	OBJECTS	{tControllerName, tSerNum, tTrapText}
	STATUS	current
	DESCRIPTION	"Protection 2. level - E-STOP - alarm disappeared"
::= { notifications 159386965 }

tESTOPL2AlarmReset	NOTIFICATION-TYPE
	OBJECTS	{tControllerName, tSerNum, tTrapText}
	STATUS	current
	DESCRIPTION	"Protection 2. level - E-STOP - alarm reset"
::= { notifications 159386966 }

tESTOPDash1L2Activated	NOTIFICATION-TYPE
	OBJECTS	{tControllerName, tSerNum, tTrapText}
	STATUS	current
	DESCRIPTION	"Protection 2. level - E-STOP_1 - alarm activated"
::= { notifications 159387776 }

tESTOPDash1L2Disappeared	NOTIFICATION-TYPE
	OBJECTS	{tControllerName, tSerNum, tTrapText}
	STATUS	current
	DESCRIPTION	"Protection 2. level - E-STOP_1 - alarm disappeared"
::= { notifications 159387777 }

tESTOPDash1L2AlarmReset	NOTIFICATION-TYPE
	OBJECTS	{tControllerName, tSerNum, tTrapText}
	STATUS	current
	DESCRIPTION	"Protection 2. level - E-STOP_1 - alarm reset"
::= { notifications 159387778 }

tESTOPDash2L2Activated	NOTIFICATION-TYPE
	OBJECTS	{tControllerName, tSerNum, tTrapText}
	STATUS	current
	DESCRIPTION	"Protection 2. level - E-STOP_2 - alarm activated"
::= { notifications 159387780 }

tESTOPDash2L2Disappeared	NOTIFICATION-TYPE
	OBJECTS	{tControllerName, tSerNum, tTrapText}
	STATUS	current
	DESCRIPTION	"Protection 2. level - E-STOP_2 - alarm disappeared"
::= { notifications 159387781 }

tESTOPDash2L2AlarmReset	NOTIFICATION-TYPE
	OBJECTS	{tControllerName, tSerNum, tTrapText}
	STATUS	current
	DESCRIPTION	"Protection 2. level - E-STOP_2 - alarm reset"
::= { notifications 159387782 }

tESTOPDash3L2Activated	NOTIFICATION-TYPE
	OBJECTS	{tControllerName, tSerNum, tTrapText}
	STATUS	current
	DESCRIPTION	"Protection 2. level - E-STOP_3 - alarm activated"
::= { notifications 159387784 }

tESTOPDash3L2Disappeared	NOTIFICATION-TYPE
	OBJECTS	{tControllerName, tSerNum, tTrapText}
	STATUS	current
	DESCRIPTION	"Protection 2. level - E-STOP_3 - alarm disappeared"
::= { notifications 159387785 }

tESTOPDash3L2AlarmReset	NOTIFICATION-TYPE
	OBJECTS	{tControllerName, tSerNum, tTrapText}
	STATUS	current
	DESCRIPTION	"Protection 2. level - E-STOP_3 - alarm reset"
::= { notifications 159387786 }

tESTOPDash4L2Activated	NOTIFICATION-TYPE
	OBJECTS	{tControllerName, tSerNum, tTrapText}
	STATUS	current
	DESCRIPTION	"Protection 2. level - E-STOP_4 - alarm activated"
::= { notifications 159387788 }

tESTOPDash4L2Disappeared	NOTIFICATION-TYPE
	OBJECTS	{tControllerName, tSerNum, tTrapText}
	STATUS	current
	DESCRIPTION	"Protection 2. level - E-STOP_4 - alarm disappeared"
::= { notifications 159387789 }

tESTOPDash4L2AlarmReset	NOTIFICATION-TYPE
	OBJECTS	{tControllerName, tSerNum, tTrapText}
	STATUS	current
	DESCRIPTION	"Protection 2. level - E-STOP_4 - alarm reset"
::= { notifications 159387790 }

tESTOPDash5L2Activated	NOTIFICATION-TYPE
	OBJECTS	{tControllerName, tSerNum, tTrapText}
	STATUS	current
	DESCRIPTION	"Protection 2. level - E-STOP_5 - alarm activated"
::= { notifications 159387792 }

tESTOPDash5L2Disappeared	NOTIFICATION-TYPE
	OBJECTS	{tControllerName, tSerNum, tTrapText}
	STATUS	current
	DESCRIPTION	"Protection 2. level - E-STOP_5 - alarm disappeared"
::= { notifications 159387793 }

tESTOPDash5L2AlarmReset	NOTIFICATION-TYPE
	OBJECTS	{tControllerName, tSerNum, tTrapText}
	STATUS	current
	DESCRIPTION	"Protection 2. level - E-STOP_5 - alarm reset"
::= { notifications 159387794 }

tESTOPDash6L2Activated	NOTIFICATION-TYPE
	OBJECTS	{tControllerName, tSerNum, tTrapText}
	STATUS	current
	DESCRIPTION	"Protection 2. level - E-STOP_6 - alarm activated"
::= { notifications 159387796 }

tESTOPDash6L2Disappeared	NOTIFICATION-TYPE
	OBJECTS	{tControllerName, tSerNum, tTrapText}
	STATUS	current
	DESCRIPTION	"Protection 2. level - E-STOP_6 - alarm disappeared"
::= { notifications 159387797 }

tESTOPDash6L2AlarmReset	NOTIFICATION-TYPE
	OBJECTS	{tControllerName, tSerNum, tTrapText}
	STATUS	current
	DESCRIPTION	"Protection 2. level - E-STOP_6 - alarm reset"
::= { notifications 159387798 }

tESTOPDash7L2Activated	NOTIFICATION-TYPE
	OBJECTS	{tControllerName, tSerNum, tTrapText}
	STATUS	current
	DESCRIPTION	"Protection 2. level - E-STOP_7 - alarm activated"
::= { notifications 159387800 }

tESTOPDash7L2Disappeared	NOTIFICATION-TYPE
	OBJECTS	{tControllerName, tSerNum, tTrapText}
	STATUS	current
	DESCRIPTION	"Protection 2. level - E-STOP_7 - alarm disappeared"
::= { notifications 159387801 }

tESTOPDash7L2AlarmReset	NOTIFICATION-TYPE
	OBJECTS	{tControllerName, tSerNum, tTrapText}
	STATUS	current
	DESCRIPTION	"Protection 2. level - E-STOP_7 - alarm reset"
::= { notifications 159387802 }

tSyncNotAllowedL1Activated	NOTIFICATION-TYPE
	OBJECTS	{tControllerName, tSerNum, tTrapText}
	STATUS	current
	DESCRIPTION	"Protection 1. level - SyncNotAllowed - alarm activated"
::= { notifications 25167632 }

tSyncNotAllowedL1Disappeared	NOTIFICATION-TYPE
	OBJECTS	{tControllerName, tSerNum, tTrapText}
	STATUS	current
	DESCRIPTION	"Protection 1. level - SyncNotAllowed - alarm disappeared"
::= { notifications 25167633 }

tSyncNotAllowedL1AlarmReset	NOTIFICATION-TYPE
	OBJECTS	{tControllerName, tSerNum, tTrapText}
	STATUS	current
	DESCRIPTION	"Protection 1. level - SyncNotAllowed - alarm reset"
::= { notifications 25167634 }

tPaveL1Activated	NOTIFICATION-TYPE
	OBJECTS	{tControllerName, tSerNum, tTrapText}
	STATUS	current
	DESCRIPTION	"Protection 1. level - Pave - alarm activated"
::= { notifications 25170136 }

tPaveL1Disappeared	NOTIFICATION-TYPE
	OBJECTS	{tControllerName, tSerNum, tTrapText}
	STATUS	current
	DESCRIPTION	"Protection 1. level - Pave - alarm disappeared"
::= { notifications 25170137 }

tPaveL1AlarmReset	NOTIFICATION-TYPE
	OBJECTS	{tControllerName, tSerNum, tTrapText}
	STATUS	current
	DESCRIPTION	"Protection 1. level - Pave - alarm reset"
::= { notifications 25170138 }

tBESSAntiIslandingL1Activated	NOTIFICATION-TYPE
	OBJECTS	{tControllerName, tSerNum, tTrapText}
	STATUS	current
	DESCRIPTION	"Protection 1. level - BESS Anti Islanding - alarm activated"
::= { notifications 25172232 }

tBESSAntiIslandingL1Disappeared	NOTIFICATION-TYPE
	OBJECTS	{tControllerName, tSerNum, tTrapText}
	STATUS	current
	DESCRIPTION	"Protection 1. level - BESS Anti Islanding - alarm disappeared"
::= { notifications 25172233 }

tBESSAntiIslandingL1AlarmReset	NOTIFICATION-TYPE
	OBJECTS	{tControllerName, tSerNum, tTrapText}
	STATUS	current
	DESCRIPTION	"Protection 1. level - BESS Anti Islanding - alarm reset"
::= { notifications 25172234 }

tMaxNumCUOnCANExceededL2Activated	NOTIFICATION-TYPE
	OBJECTS	{tControllerName, tSerNum, tTrapText}
	STATUS	current
	DESCRIPTION	"Protection 2. level - Max Num CU on CAN Exceeded - alarm activated"
::= { notifications 159390056 }

tMaxNumCUOnCANExceededL2Disappeared	NOTIFICATION-TYPE
	OBJECTS	{tControllerName, tSerNum, tTrapText}
	STATUS	current
	DESCRIPTION	"Protection 2. level - Max Num CU on CAN Exceeded - alarm disappeared"
::= { notifications 159390057 }

tMaxNumCUOnCANExceededL2AlarmReset	NOTIFICATION-TYPE
	OBJECTS	{tControllerName, tSerNum, tTrapText}
	STATUS	current
	DESCRIPTION	"Protection 2. level - Max Num CU on CAN Exceeded - alarm reset"
::= { notifications 159390058 }

tCANModule1L1Activated	NOTIFICATION-TYPE
	OBJECTS	{tControllerName, tSerNum, tTrapText}
	STATUS	current
	DESCRIPTION	"Protection 1. level - CAN Module 1 - alarm activated"
::= { notifications 33557856 }

tCANModule1L1Disappeared	NOTIFICATION-TYPE
	OBJECTS	{tControllerName, tSerNum, tTrapText}
	STATUS	current
	DESCRIPTION	"Protection 1. level - CAN Module 1 - alarm disappeared"
::= { notifications 33557857 }

tCANModule1L1AlarmReset	NOTIFICATION-TYPE
	OBJECTS	{tControllerName, tSerNum, tTrapText}
	STATUS	current
	DESCRIPTION	"Protection 1. level - CAN Module 1 - alarm reset"
::= { notifications 33557858 }

tCANModule1L2Activated	NOTIFICATION-TYPE
	OBJECTS	{tControllerName, tSerNum, tTrapText}
	STATUS	current
	DESCRIPTION	"Protection 2. level - CAN Module 1 - alarm activated"
::= { notifications 167775584 }

tCANModule1L2Disappeared	NOTIFICATION-TYPE
	OBJECTS	{tControllerName, tSerNum, tTrapText}
	STATUS	current
	DESCRIPTION	"Protection 2. level - CAN Module 1 - alarm disappeared"
::= { notifications 167775585 }

tCANModule1L2AlarmReset	NOTIFICATION-TYPE
	OBJECTS	{tControllerName, tSerNum, tTrapText}
	STATUS	current
	DESCRIPTION	"Protection 2. level - CAN Module 1 - alarm reset"
::= { notifications 167775586 }

tModuleCHR3ASlot2L1Activated	NOTIFICATION-TYPE
	OBJECTS	{tControllerName, tSerNum, tTrapText}
	STATUS	current
	DESCRIPTION	"Protection 1. level - Module: Slot 2 - alarm activated"
::= { notifications 33557860 }

tModuleCHR3ASlot2L1Disappeared	NOTIFICATION-TYPE
	OBJECTS	{tControllerName, tSerNum, tTrapText}
	STATUS	current
	DESCRIPTION	"Protection 1. level - Module: Slot 2 - alarm disappeared"
::= { notifications 33557861 }

tModuleCHR3ASlot2L1AlarmReset	NOTIFICATION-TYPE
	OBJECTS	{tControllerName, tSerNum, tTrapText}
	STATUS	current
	DESCRIPTION	"Protection 1. level - Module: Slot 2 - alarm reset"
::= { notifications 33557862 }

tModuleCHR3ASlot2L2Activated	NOTIFICATION-TYPE
	OBJECTS	{tControllerName, tSerNum, tTrapText}
	STATUS	current
	DESCRIPTION	"Protection 2. level - Module: Slot 2 - alarm activated"
::= { notifications 167775588 }

tModuleCHR3ASlot2L2Disappeared	NOTIFICATION-TYPE
	OBJECTS	{tControllerName, tSerNum, tTrapText}
	STATUS	current
	DESCRIPTION	"Protection 2. level - Module: Slot 2 - alarm disappeared"
::= { notifications 167775589 }

tModuleCHR3ASlot2L2AlarmReset	NOTIFICATION-TYPE
	OBJECTS	{tControllerName, tSerNum, tTrapText}
	STATUS	current
	DESCRIPTION	"Protection 2. level - Module: Slot 2 - alarm reset"
::= { notifications 167775590 }

tModuleCHR3ASlot3L1Activated	NOTIFICATION-TYPE
	OBJECTS	{tControllerName, tSerNum, tTrapText}
	STATUS	current
	DESCRIPTION	"Protection 1. level - Module: Slot 3 - alarm activated"
::= { notifications 33558612 }

tModuleCHR3ASlot3L1Disappeared	NOTIFICATION-TYPE
	OBJECTS	{tControllerName, tSerNum, tTrapText}
	STATUS	current
	DESCRIPTION	"Protection 1. level - Module: Slot 3 - alarm disappeared"
::= { notifications 33558613 }

tModuleCHR3ASlot3L1AlarmReset	NOTIFICATION-TYPE
	OBJECTS	{tControllerName, tSerNum, tTrapText}
	STATUS	current
	DESCRIPTION	"Protection 1. level - Module: Slot 3 - alarm reset"
::= { notifications 33558614 }

tModuleCHR3ASlot3L2Activated	NOTIFICATION-TYPE
	OBJECTS	{tControllerName, tSerNum, tTrapText}
	STATUS	current
	DESCRIPTION	"Protection 2. level - Module: Slot 3 - alarm activated"
::= { notifications 167776340 }

tModuleCHR3ASlot3L2Disappeared	NOTIFICATION-TYPE
	OBJECTS	{tControllerName, tSerNum, tTrapText}
	STATUS	current
	DESCRIPTION	"Protection 2. level - Module: Slot 3 - alarm disappeared"
::= { notifications 167776341 }

tModuleCHR3ASlot3L2AlarmReset	NOTIFICATION-TYPE
	OBJECTS	{tControllerName, tSerNum, tTrapText}
	STATUS	current
	DESCRIPTION	"Protection 2. level - Module: Slot 3 - alarm reset"
::= { notifications 167776342 }

tModuleCHR3ASlot4L1Activated	NOTIFICATION-TYPE
	OBJECTS	{tControllerName, tSerNum, tTrapText}
	STATUS	current
	DESCRIPTION	"Protection 1. level - Module: Slot 4 - alarm activated"
::= { notifications 33558616 }

tModuleCHR3ASlot4L1Disappeared	NOTIFICATION-TYPE
	OBJECTS	{tControllerName, tSerNum, tTrapText}
	STATUS	current
	DESCRIPTION	"Protection 1. level - Module: Slot 4 - alarm disappeared"
::= { notifications 33558617 }

tModuleCHR3ASlot4L1AlarmReset	NOTIFICATION-TYPE
	OBJECTS	{tControllerName, tSerNum, tTrapText}
	STATUS	current
	DESCRIPTION	"Protection 1. level - Module: Slot 4 - alarm reset"
::= { notifications 33558618 }

tModuleCHR3ASlot4L2Activated	NOTIFICATION-TYPE
	OBJECTS	{tControllerName, tSerNum, tTrapText}
	STATUS	current
	DESCRIPTION	"Protection 2. level - Module: Slot 4 - alarm activated"
::= { notifications 167776344 }

tModuleCHR3ASlot4L2Disappeared	NOTIFICATION-TYPE
	OBJECTS	{tControllerName, tSerNum, tTrapText}
	STATUS	current
	DESCRIPTION	"Protection 2. level - Module: Slot 4 - alarm disappeared"
::= { notifications 167776345 }

tModuleCHR3ASlot4L2AlarmReset	NOTIFICATION-TYPE
	OBJECTS	{tControllerName, tSerNum, tTrapText}
	STATUS	current
	DESCRIPTION	"Protection 2. level - Module: Slot 4 - alarm reset"
::= { notifications 167776346 }

tModuleCHR3ASlot5L1Activated	NOTIFICATION-TYPE
	OBJECTS	{tControllerName, tSerNum, tTrapText}
	STATUS	current
	DESCRIPTION	"Protection 1. level - Module: Slot 5 - alarm activated"
::= { notifications 33558620 }

tModuleCHR3ASlot5L1Disappeared	NOTIFICATION-TYPE
	OBJECTS	{tControllerName, tSerNum, tTrapText}
	STATUS	current
	DESCRIPTION	"Protection 1. level - Module: Slot 5 - alarm disappeared"
::= { notifications 33558621 }

tModuleCHR3ASlot5L1AlarmReset	NOTIFICATION-TYPE
	OBJECTS	{tControllerName, tSerNum, tTrapText}
	STATUS	current
	DESCRIPTION	"Protection 1. level - Module: Slot 5 - alarm reset"
::= { notifications 33558622 }

tModuleCHR3ASlot5L2Activated	NOTIFICATION-TYPE
	OBJECTS	{tControllerName, tSerNum, tTrapText}
	STATUS	current
	DESCRIPTION	"Protection 2. level - Module: Slot 5 - alarm activated"
::= { notifications 167776348 }

tModuleCHR3ASlot5L2Disappeared	NOTIFICATION-TYPE
	OBJECTS	{tControllerName, tSerNum, tTrapText}
	STATUS	current
	DESCRIPTION	"Protection 2. level - Module: Slot 5 - alarm disappeared"
::= { notifications 167776349 }

tModuleCHR3ASlot5L2AlarmReset	NOTIFICATION-TYPE
	OBJECTS	{tControllerName, tSerNum, tTrapText}
	STATUS	current
	DESCRIPTION	"Protection 2. level - Module: Slot 5 - alarm reset"
::= { notifications 167776350 }

tModuleBroSlotABrcFalseModuleL1Activated	NOTIFICATION-TYPE
	OBJECTS	{tControllerName, tSerNum, tTrapText}
	STATUS	current
	DESCRIPTION	"Protection 1. level - Module(slotA) - false module - alarm activated"
::= { notifications 33557424 }

tModuleBroSlotABrcFalseModuleL1Disappeared	NOTIFICATION-TYPE
	OBJECTS	{tControllerName, tSerNum, tTrapText}
	STATUS	current
	DESCRIPTION	"Protection 1. level - Module(slotA) - false module - alarm disappeared"
::= { notifications 33557425 }

tModuleBroSlotABrcFalseModuleL1AlarmReset	NOTIFICATION-TYPE
	OBJECTS	{tControllerName, tSerNum, tTrapText}
	STATUS	current
	DESCRIPTION	"Protection 1. level - Module(slotA) - false module - alarm reset"
::= { notifications 33557426 }

tModuleBroSlotABrcFalseModuleL2Activated	NOTIFICATION-TYPE
	OBJECTS	{tControllerName, tSerNum, tTrapText}
	STATUS	current
	DESCRIPTION	"Protection 2. level - Module(slotA) - false module - alarm activated"
::= { notifications 167775152 }

tModuleBroSlotABrcFalseModuleL2Disappeared	NOTIFICATION-TYPE
	OBJECTS	{tControllerName, tSerNum, tTrapText}
	STATUS	current
	DESCRIPTION	"Protection 2. level - Module(slotA) - false module - alarm disappeared"
::= { notifications 167775153 }

tModuleBroSlotABrcFalseModuleL2AlarmReset	NOTIFICATION-TYPE
	OBJECTS	{tControllerName, tSerNum, tTrapText}
	STATUS	current
	DESCRIPTION	"Protection 2. level - Module(slotA) - false module - alarm reset"
::= { notifications 167775154 }

tModuleBroSlotBBrcFalseModuleL1Activated	NOTIFICATION-TYPE
	OBJECTS	{tControllerName, tSerNum, tTrapText}
	STATUS	current
	DESCRIPTION	"Protection 1. level - Module(slotB) - false module - alarm activated"
::= { notifications 33557448 }

tModuleBroSlotBBrcFalseModuleL1Disappeared	NOTIFICATION-TYPE
	OBJECTS	{tControllerName, tSerNum, tTrapText}
	STATUS	current
	DESCRIPTION	"Protection 1. level - Module(slotB) - false module - alarm disappeared"
::= { notifications 33557449 }

tModuleBroSlotBBrcFalseModuleL1AlarmReset	NOTIFICATION-TYPE
	OBJECTS	{tControllerName, tSerNum, tTrapText}
	STATUS	current
	DESCRIPTION	"Protection 1. level - Module(slotB) - false module - alarm reset"
::= { notifications 33557450 }

tModuleBroSlotBBrcFalseModuleL2Activated	NOTIFICATION-TYPE
	OBJECTS	{tControllerName, tSerNum, tTrapText}
	STATUS	current
	DESCRIPTION	"Protection 2. level - Module(slotB) - false module - alarm activated"
::= { notifications 167775176 }

tModuleBroSlotBBrcFalseModuleL2Disappeared	NOTIFICATION-TYPE
	OBJECTS	{tControllerName, tSerNum, tTrapText}
	STATUS	current
	DESCRIPTION	"Protection 2. level - Module(slotB) - false module - alarm disappeared"
::= { notifications 167775177 }

tModuleBroSlotBBrcFalseModuleL2AlarmReset	NOTIFICATION-TYPE
	OBJECTS	{tControllerName, tSerNum, tTrapText}
	STATUS	current
	DESCRIPTION	"Protection 2. level - Module(slotB) - false module - alarm reset"
::= { notifications 167775178 }

tModuleBroSlotABrcUnknownModuleL1Activated	NOTIFICATION-TYPE
	OBJECTS	{tControllerName, tSerNum, tTrapText}
	STATUS	current
	DESCRIPTION	"Protection 1. level - Module(slotA) - unknown module - alarm activated"
::= { notifications 33557428 }

tModuleBroSlotABrcUnknownModuleL1Disappeared	NOTIFICATION-TYPE
	OBJECTS	{tControllerName, tSerNum, tTrapText}
	STATUS	current
	DESCRIPTION	"Protection 1. level - Module(slotA) - unknown module - alarm disappeared"
::= { notifications 33557429 }

tModuleBroSlotABrcUnknownModuleL1AlarmReset	NOTIFICATION-TYPE
	OBJECTS	{tControllerName, tSerNum, tTrapText}
	STATUS	current
	DESCRIPTION	"Protection 1. level - Module(slotA) - unknown module - alarm reset"
::= { notifications 33557430 }

tModuleBroSlotABrcUnknownModuleL2Activated	NOTIFICATION-TYPE
	OBJECTS	{tControllerName, tSerNum, tTrapText}
	STATUS	current
	DESCRIPTION	"Protection 2. level - Module(slotA) - unknown module - alarm activated"
::= { notifications 167775156 }

tModuleBroSlotABrcUnknownModuleL2Disappeared	NOTIFICATION-TYPE
	OBJECTS	{tControllerName, tSerNum, tTrapText}
	STATUS	current
	DESCRIPTION	"Protection 2. level - Module(slotA) - unknown module - alarm disappeared"
::= { notifications 167775157 }

tModuleBroSlotABrcUnknownModuleL2AlarmReset	NOTIFICATION-TYPE
	OBJECTS	{tControllerName, tSerNum, tTrapText}
	STATUS	current
	DESCRIPTION	"Protection 2. level - Module(slotA) - unknown module - alarm reset"
::= { notifications 167775158 }

tModuleBroSlotBBrcUnknownModuleL1Activated	NOTIFICATION-TYPE
	OBJECTS	{tControllerName, tSerNum, tTrapText}
	STATUS	current
	DESCRIPTION	"Protection 1. level - Module(slotB) - unknown module - alarm activated"
::= { notifications 33557452 }

tModuleBroSlotBBrcUnknownModuleL1Disappeared	NOTIFICATION-TYPE
	OBJECTS	{tControllerName, tSerNum, tTrapText}
	STATUS	current
	DESCRIPTION	"Protection 1. level - Module(slotB) - unknown module - alarm disappeared"
::= { notifications 33557453 }

tModuleBroSlotBBrcUnknownModuleL1AlarmReset	NOTIFICATION-TYPE
	OBJECTS	{tControllerName, tSerNum, tTrapText}
	STATUS	current
	DESCRIPTION	"Protection 1. level - Module(slotB) - unknown module - alarm reset"
::= { notifications 33557454 }

tModuleBroSlotBBrcUnknownModuleL2Activated	NOTIFICATION-TYPE
	OBJECTS	{tControllerName, tSerNum, tTrapText}
	STATUS	current
	DESCRIPTION	"Protection 2. level - Module(slotB) - unknown module - alarm activated"
::= { notifications 167775180 }

tModuleBroSlotBBrcUnknownModuleL2Disappeared	NOTIFICATION-TYPE
	OBJECTS	{tControllerName, tSerNum, tTrapText}
	STATUS	current
	DESCRIPTION	"Protection 2. level - Module(slotB) - unknown module - alarm disappeared"
::= { notifications 167775181 }

tModuleBroSlotBBrcUnknownModuleL2AlarmReset	NOTIFICATION-TYPE
	OBJECTS	{tControllerName, tSerNum, tTrapText}
	STATUS	current
	DESCRIPTION	"Protection 2. level - Module(slotB) - unknown module - alarm reset"
::= { notifications 167775182 }

tModuleBroSlotABrcUnattendedL1Activated	NOTIFICATION-TYPE
	OBJECTS	{tControllerName, tSerNum, tTrapText}
	STATUS	current
	DESCRIPTION	"Protection 1. level - Module(slotA) - unattended - alarm activated"
::= { notifications 33557432 }

tModuleBroSlotABrcUnattendedL1Disappeared	NOTIFICATION-TYPE
	OBJECTS	{tControllerName, tSerNum, tTrapText}
	STATUS	current
	DESCRIPTION	"Protection 1. level - Module(slotA) - unattended - alarm disappeared"
::= { notifications 33557433 }

tModuleBroSlotABrcUnattendedL1AlarmReset	NOTIFICATION-TYPE
	OBJECTS	{tControllerName, tSerNum, tTrapText}
	STATUS	current
	DESCRIPTION	"Protection 1. level - Module(slotA) - unattended - alarm reset"
::= { notifications 33557434 }

tModuleBroSlotABrcUnattendedL2Activated	NOTIFICATION-TYPE
	OBJECTS	{tControllerName, tSerNum, tTrapText}
	STATUS	current
	DESCRIPTION	"Protection 2. level - Module(slotA) - unattended - alarm activated"
::= { notifications 167775160 }

tModuleBroSlotABrcUnattendedL2Disappeared	NOTIFICATION-TYPE
	OBJECTS	{tControllerName, tSerNum, tTrapText}
	STATUS	current
	DESCRIPTION	"Protection 2. level - Module(slotA) - unattended - alarm disappeared"
::= { notifications 167775161 }

tModuleBroSlotABrcUnattendedL2AlarmReset	NOTIFICATION-TYPE
	OBJECTS	{tControllerName, tSerNum, tTrapText}
	STATUS	current
	DESCRIPTION	"Protection 2. level - Module(slotA) - unattended - alarm reset"
::= { notifications 167775162 }

tModuleBroSlotBBrcUnattendedL1Activated	NOTIFICATION-TYPE
	OBJECTS	{tControllerName, tSerNum, tTrapText}
	STATUS	current
	DESCRIPTION	"Protection 1. level - Module(slotB) - unattended - alarm activated"
::= { notifications 33557456 }

tModuleBroSlotBBrcUnattendedL1Disappeared	NOTIFICATION-TYPE
	OBJECTS	{tControllerName, tSerNum, tTrapText}
	STATUS	current
	DESCRIPTION	"Protection 1. level - Module(slotB) - unattended - alarm disappeared"
::= { notifications 33557457 }

tModuleBroSlotBBrcUnattendedL1AlarmReset	NOTIFICATION-TYPE
	OBJECTS	{tControllerName, tSerNum, tTrapText}
	STATUS	current
	DESCRIPTION	"Protection 1. level - Module(slotB) - unattended - alarm reset"
::= { notifications 33557458 }

tModuleBroSlotBBrcUnattendedL2Activated	NOTIFICATION-TYPE
	OBJECTS	{tControllerName, tSerNum, tTrapText}
	STATUS	current
	DESCRIPTION	"Protection 2. level - Module(slotB) - unattended - alarm activated"
::= { notifications 167775184 }

tModuleBroSlotBBrcUnattendedL2Disappeared	NOTIFICATION-TYPE
	OBJECTS	{tControllerName, tSerNum, tTrapText}
	STATUS	current
	DESCRIPTION	"Protection 2. level - Module(slotB) - unattended - alarm disappeared"
::= { notifications 167775185 }

tModuleBroSlotBBrcUnattendedL2AlarmReset	NOTIFICATION-TYPE
	OBJECTS	{tControllerName, tSerNum, tTrapText}
	STATUS	current
	DESCRIPTION	"Protection 2. level - Module(slotB) - unattended - alarm reset"
::= { notifications 167775186 }

tModuleBroSlotABrcCommCHR2EOutageL1Activated	NOTIFICATION-TYPE
	OBJECTS	{tControllerName, tSerNum, tTrapText}
	STATUS	current
	DESCRIPTION	"Protection 1. level - Module(slotA) - comm. outage - alarm activated"
::= { notifications 33557440 }

tModuleBroSlotABrcCommCHR2EOutageL1Disappeared	NOTIFICATION-TYPE
	OBJECTS	{tControllerName, tSerNum, tTrapText}
	STATUS	current
	DESCRIPTION	"Protection 1. level - Module(slotA) - comm. outage - alarm disappeared"
::= { notifications 33557441 }

tModuleBroSlotABrcCommCHR2EOutageL1AlarmReset	NOTIFICATION-TYPE
	OBJECTS	{tControllerName, tSerNum, tTrapText}
	STATUS	current
	DESCRIPTION	"Protection 1. level - Module(slotA) - comm. outage - alarm reset"
::= { notifications 33557442 }

tModuleBroSlotABrcCommCHR2EOutageL2Activated	NOTIFICATION-TYPE
	OBJECTS	{tControllerName, tSerNum, tTrapText}
	STATUS	current
	DESCRIPTION	"Protection 2. level - Module(slotA) - comm. outage - alarm activated"
::= { notifications 167775168 }

tModuleBroSlotABrcCommCHR2EOutageL2Disappeared	NOTIFICATION-TYPE
	OBJECTS	{tControllerName, tSerNum, tTrapText}
	STATUS	current
	DESCRIPTION	"Protection 2. level - Module(slotA) - comm. outage - alarm disappeared"
::= { notifications 167775169 }

tModuleBroSlotABrcCommCHR2EOutageL2AlarmReset	NOTIFICATION-TYPE
	OBJECTS	{tControllerName, tSerNum, tTrapText}
	STATUS	current
	DESCRIPTION	"Protection 2. level - Module(slotA) - comm. outage - alarm reset"
::= { notifications 167775170 }

tModuleBroSlotBBrcCommCHR2EOutageL1Activated	NOTIFICATION-TYPE
	OBJECTS	{tControllerName, tSerNum, tTrapText}
	STATUS	current
	DESCRIPTION	"Protection 1. level - Module(slotB) - comm. outage - alarm activated"
::= { notifications 33557464 }

tModuleBroSlotBBrcCommCHR2EOutageL1Disappeared	NOTIFICATION-TYPE
	OBJECTS	{tControllerName, tSerNum, tTrapText}
	STATUS	current
	DESCRIPTION	"Protection 1. level - Module(slotB) - comm. outage - alarm disappeared"
::= { notifications 33557465 }

tModuleBroSlotBBrcCommCHR2EOutageL1AlarmReset	NOTIFICATION-TYPE
	OBJECTS	{tControllerName, tSerNum, tTrapText}
	STATUS	current
	DESCRIPTION	"Protection 1. level - Module(slotB) - comm. outage - alarm reset"
::= { notifications 33557466 }

tModuleBroSlotBBrcCommCHR2EOutageL2Activated	NOTIFICATION-TYPE
	OBJECTS	{tControllerName, tSerNum, tTrapText}
	STATUS	current
	DESCRIPTION	"Protection 2. level - Module(slotB) - comm. outage - alarm activated"
::= { notifications 167775192 }

tModuleBroSlotBBrcCommCHR2EOutageL2Disappeared	NOTIFICATION-TYPE
	OBJECTS	{tControllerName, tSerNum, tTrapText}
	STATUS	current
	DESCRIPTION	"Protection 2. level - Module(slotB) - comm. outage - alarm disappeared"
::= { notifications 167775193 }

tModuleBroSlotBBrcCommCHR2EOutageL2AlarmReset	NOTIFICATION-TYPE
	OBJECTS	{tControllerName, tSerNum, tTrapText}
	STATUS	current
	DESCRIPTION	"Protection 2. level - Module(slotB) - comm. outage - alarm reset"
::= { notifications 167775194 }

tModuleBroSlotABrcUnexpectedL1Activated	NOTIFICATION-TYPE
	OBJECTS	{tControllerName, tSerNum, tTrapText}
	STATUS	current
	DESCRIPTION	"Protection 1. level - Module(slotA) - unexpected - alarm activated"
::= { notifications 33557472 }

tModuleBroSlotABrcUnexpectedL1Disappeared	NOTIFICATION-TYPE
	OBJECTS	{tControllerName, tSerNum, tTrapText}
	STATUS	current
	DESCRIPTION	"Protection 1. level - Module(slotA) - unexpected - alarm disappeared"
::= { notifications 33557473 }

tModuleBroSlotABrcUnexpectedL1AlarmReset	NOTIFICATION-TYPE
	OBJECTS	{tControllerName, tSerNum, tTrapText}
	STATUS	current
	DESCRIPTION	"Protection 1. level - Module(slotA) - unexpected - alarm reset"
::= { notifications 33557474 }

tModuleBroSlotABrcUnexpectedL2Activated	NOTIFICATION-TYPE
	OBJECTS	{tControllerName, tSerNum, tTrapText}
	STATUS	current
	DESCRIPTION	"Protection 2. level - Module(slotA) - unexpected - alarm activated"
::= { notifications 167775200 }

tModuleBroSlotABrcUnexpectedL2Disappeared	NOTIFICATION-TYPE
	OBJECTS	{tControllerName, tSerNum, tTrapText}
	STATUS	current
	DESCRIPTION	"Protection 2. level - Module(slotA) - unexpected - alarm disappeared"
::= { notifications 167775201 }

tModuleBroSlotABrcUnexpectedL2AlarmReset	NOTIFICATION-TYPE
	OBJECTS	{tControllerName, tSerNum, tTrapText}
	STATUS	current
	DESCRIPTION	"Protection 2. level - Module(slotA) - unexpected - alarm reset"
::= { notifications 167775202 }

tModuleBroSlotBBrcUnexpectedL1Activated	NOTIFICATION-TYPE
	OBJECTS	{tControllerName, tSerNum, tTrapText}
	STATUS	current
	DESCRIPTION	"Protection 1. level - Module(slotB) - unexpected - alarm activated"
::= { notifications 33557476 }

tModuleBroSlotBBrcUnexpectedL1Disappeared	NOTIFICATION-TYPE
	OBJECTS	{tControllerName, tSerNum, tTrapText}
	STATUS	current
	DESCRIPTION	"Protection 1. level - Module(slotB) - unexpected - alarm disappeared"
::= { notifications 33557477 }

tModuleBroSlotBBrcUnexpectedL1AlarmReset	NOTIFICATION-TYPE
	OBJECTS	{tControllerName, tSerNum, tTrapText}
	STATUS	current
	DESCRIPTION	"Protection 1. level - Module(slotB) - unexpected - alarm reset"
::= { notifications 33557478 }

tModuleBroSlotBBrcUnexpectedL2Activated	NOTIFICATION-TYPE
	OBJECTS	{tControllerName, tSerNum, tTrapText}
	STATUS	current
	DESCRIPTION	"Protection 2. level - Module(slotB) - unexpected - alarm activated"
::= { notifications 167775204 }

tModuleBroSlotBBrcUnexpectedL2Disappeared	NOTIFICATION-TYPE
	OBJECTS	{tControllerName, tSerNum, tTrapText}
	STATUS	current
	DESCRIPTION	"Protection 2. level - Module(slotB) - unexpected - alarm disappeared"
::= { notifications 167775205 }

tModuleBroSlotBBrcUnexpectedL2AlarmReset	NOTIFICATION-TYPE
	OBJECTS	{tControllerName, tSerNum, tTrapText}
	STATUS	current
	DESCRIPTION	"Protection 2. level - Module(slotB) - unexpected - alarm reset"
::= { notifications 167775206 }

tEMBroABrcAMessageLostL1Activated	NOTIFICATION-TYPE
	OBJECTS	{tControllerName, tSerNum, tTrapText}
	STATUS	current
	DESCRIPTION	"Protection 1. level - EM(A) - a message lost - alarm activated"
::= { notifications 33557436 }

tEMBroABrcAMessageLostL1Disappeared	NOTIFICATION-TYPE
	OBJECTS	{tControllerName, tSerNum, tTrapText}
	STATUS	current
	DESCRIPTION	"Protection 1. level - EM(A) - a message lost - alarm disappeared"
::= { notifications 33557437 }

tEMBroABrcAMessageLostL1AlarmReset	NOTIFICATION-TYPE
	OBJECTS	{tControllerName, tSerNum, tTrapText}
	STATUS	current
	DESCRIPTION	"Protection 1. level - EM(A) - a message lost - alarm reset"
::= { notifications 33557438 }

tEMBroABrcAMessageLostL2Activated	NOTIFICATION-TYPE
	OBJECTS	{tControllerName, tSerNum, tTrapText}
	STATUS	current
	DESCRIPTION	"Protection 2. level - EM(A) - a message lost - alarm activated"
::= { notifications 167775164 }

tEMBroABrcAMessageLostL2Disappeared	NOTIFICATION-TYPE
	OBJECTS	{tControllerName, tSerNum, tTrapText}
	STATUS	current
	DESCRIPTION	"Protection 2. level - EM(A) - a message lost - alarm disappeared"
::= { notifications 167775165 }

tEMBroABrcAMessageLostL2AlarmReset	NOTIFICATION-TYPE
	OBJECTS	{tControllerName, tSerNum, tTrapText}
	STATUS	current
	DESCRIPTION	"Protection 2. level - EM(A) - a message lost - alarm reset"
::= { notifications 167775166 }

tEMBroBBrcAMessageLostL1Activated	NOTIFICATION-TYPE
	OBJECTS	{tControllerName, tSerNum, tTrapText}
	STATUS	current
	DESCRIPTION	"Protection 1. level - EM(B) - a message lost - alarm activated"
::= { notifications 33557460 }

tEMBroBBrcAMessageLostL1Disappeared	NOTIFICATION-TYPE
	OBJECTS	{tControllerName, tSerNum, tTrapText}
	STATUS	current
	DESCRIPTION	"Protection 1. level - EM(B) - a message lost - alarm disappeared"
::= { notifications 33557461 }

tEMBroBBrcAMessageLostL1AlarmReset	NOTIFICATION-TYPE
	OBJECTS	{tControllerName, tSerNum, tTrapText}
	STATUS	current
	DESCRIPTION	"Protection 1. level - EM(B) - a message lost - alarm reset"
::= { notifications 33557462 }

tEMBroBBrcAMessageLostL2Activated	NOTIFICATION-TYPE
	OBJECTS	{tControllerName, tSerNum, tTrapText}
	STATUS	current
	DESCRIPTION	"Protection 2. level - EM(B) - a message lost - alarm activated"
::= { notifications 167775188 }

tEMBroBBrcAMessageLostL2Disappeared	NOTIFICATION-TYPE
	OBJECTS	{tControllerName, tSerNum, tTrapText}
	STATUS	current
	DESCRIPTION	"Protection 2. level - EM(B) - a message lost - alarm disappeared"
::= { notifications 167775189 }

tEMBroBBrcAMessageLostL2AlarmReset	NOTIFICATION-TYPE
	OBJECTS	{tControllerName, tSerNum, tTrapText}
	STATUS	current
	DESCRIPTION	"Protection 2. level - EM(B) - a message lost - alarm reset"
::= { notifications 167775190 }

tEMBroABrcConfigurationMistakeL1Activated	NOTIFICATION-TYPE
	OBJECTS	{tControllerName, tSerNum, tTrapText}
	STATUS	current
	DESCRIPTION	"Protection 1. level - EM(A) - configuration mistake - alarm activated"
::= { notifications 33557480 }

tEMBroABrcConfigurationMistakeL1Disappeared	NOTIFICATION-TYPE
	OBJECTS	{tControllerName, tSerNum, tTrapText}
	STATUS	current
	DESCRIPTION	"Protection 1. level - EM(A) - configuration mistake - alarm disappeared"
::= { notifications 33557481 }

tEMBroABrcConfigurationMistakeL1AlarmReset	NOTIFICATION-TYPE
	OBJECTS	{tControllerName, tSerNum, tTrapText}
	STATUS	current
	DESCRIPTION	"Protection 1. level - EM(A) - configuration mistake - alarm reset"
::= { notifications 33557482 }

tEMBroABrcConfigurationMistakeL2Activated	NOTIFICATION-TYPE
	OBJECTS	{tControllerName, tSerNum, tTrapText}
	STATUS	current
	DESCRIPTION	"Protection 2. level - EM(A) - configuration mistake - alarm activated"
::= { notifications 167775208 }

tEMBroABrcConfigurationMistakeL2Disappeared	NOTIFICATION-TYPE
	OBJECTS	{tControllerName, tSerNum, tTrapText}
	STATUS	current
	DESCRIPTION	"Protection 2. level - EM(A) - configuration mistake - alarm disappeared"
::= { notifications 167775209 }

tEMBroABrcConfigurationMistakeL2AlarmReset	NOTIFICATION-TYPE
	OBJECTS	{tControllerName, tSerNum, tTrapText}
	STATUS	current
	DESCRIPTION	"Protection 2. level - EM(A) - configuration mistake - alarm reset"
::= { notifications 167775210 }

tEMBroBBrcConfigurationMistakeL1Activated	NOTIFICATION-TYPE
	OBJECTS	{tControllerName, tSerNum, tTrapText}
	STATUS	current
	DESCRIPTION	"Protection 1. level - EM(B) - configuration mistake - alarm activated"
::= { notifications 33557484 }

tEMBroBBrcConfigurationMistakeL1Disappeared	NOTIFICATION-TYPE
	OBJECTS	{tControllerName, tSerNum, tTrapText}
	STATUS	current
	DESCRIPTION	"Protection 1. level - EM(B) - configuration mistake - alarm disappeared"
::= { notifications 33557485 }

tEMBroBBrcConfigurationMistakeL1AlarmReset	NOTIFICATION-TYPE
	OBJECTS	{tControllerName, tSerNum, tTrapText}
	STATUS	current
	DESCRIPTION	"Protection 1. level - EM(B) - configuration mistake - alarm reset"
::= { notifications 33557486 }

tEMBroBBrcConfigurationMistakeL2Activated	NOTIFICATION-TYPE
	OBJECTS	{tControllerName, tSerNum, tTrapText}
	STATUS	current
	DESCRIPTION	"Protection 2. level - EM(B) - configuration mistake - alarm activated"
::= { notifications 167775212 }

tEMBroBBrcConfigurationMistakeL2Disappeared	NOTIFICATION-TYPE
	OBJECTS	{tControllerName, tSerNum, tTrapText}
	STATUS	current
	DESCRIPTION	"Protection 2. level - EM(B) - configuration mistake - alarm disappeared"
::= { notifications 167775213 }

tEMBroBBrcConfigurationMistakeL2AlarmReset	NOTIFICATION-TYPE
	OBJECTS	{tControllerName, tSerNum, tTrapText}
	STATUS	current
	DESCRIPTION	"Protection 2. level - EM(B) - configuration mistake - alarm reset"
::= { notifications 167775214 }

tEMBroABrcInsufficientL1Activated	NOTIFICATION-TYPE
	OBJECTS	{tControllerName, tSerNum, tTrapText}
	STATUS	current
	DESCRIPTION	"Protection 1. level - EM(A) - insufficient - alarm activated"
::= { notifications 33557488 }

tEMBroABrcInsufficientL1Disappeared	NOTIFICATION-TYPE
	OBJECTS	{tControllerName, tSerNum, tTrapText}
	STATUS	current
	DESCRIPTION	"Protection 1. level - EM(A) - insufficient - alarm disappeared"
::= { notifications 33557489 }

tEMBroABrcInsufficientL1AlarmReset	NOTIFICATION-TYPE
	OBJECTS	{tControllerName, tSerNum, tTrapText}
	STATUS	current
	DESCRIPTION	"Protection 1. level - EM(A) - insufficient - alarm reset"
::= { notifications 33557490 }

tEMBroABrcInsufficientL2Activated	NOTIFICATION-TYPE
	OBJECTS	{tControllerName, tSerNum, tTrapText}
	STATUS	current
	DESCRIPTION	"Protection 2. level - EM(A) - insufficient - alarm activated"
::= { notifications 167775216 }

tEMBroABrcInsufficientL2Disappeared	NOTIFICATION-TYPE
	OBJECTS	{tControllerName, tSerNum, tTrapText}
	STATUS	current
	DESCRIPTION	"Protection 2. level - EM(A) - insufficient - alarm disappeared"
::= { notifications 167775217 }

tEMBroABrcInsufficientL2AlarmReset	NOTIFICATION-TYPE
	OBJECTS	{tControllerName, tSerNum, tTrapText}
	STATUS	current
	DESCRIPTION	"Protection 2. level - EM(A) - insufficient - alarm reset"
::= { notifications 167775218 }

tEMBroBBrcInsufficientL1Activated	NOTIFICATION-TYPE
	OBJECTS	{tControllerName, tSerNum, tTrapText}
	STATUS	current
	DESCRIPTION	"Protection 1. level - EM(B) - insufficient - alarm activated"
::= { notifications 33557492 }

tEMBroBBrcInsufficientL1Disappeared	NOTIFICATION-TYPE
	OBJECTS	{tControllerName, tSerNum, tTrapText}
	STATUS	current
	DESCRIPTION	"Protection 1. level - EM(B) - insufficient - alarm disappeared"
::= { notifications 33557493 }

tEMBroBBrcInsufficientL1AlarmReset	NOTIFICATION-TYPE
	OBJECTS	{tControllerName, tSerNum, tTrapText}
	STATUS	current
	DESCRIPTION	"Protection 1. level - EM(B) - insufficient - alarm reset"
::= { notifications 33557494 }

tEMBroBBrcInsufficientL2Activated	NOTIFICATION-TYPE
	OBJECTS	{tControllerName, tSerNum, tTrapText}
	STATUS	current
	DESCRIPTION	"Protection 2. level - EM(B) - insufficient - alarm activated"
::= { notifications 167775220 }

tEMBroBBrcInsufficientL2Disappeared	NOTIFICATION-TYPE
	OBJECTS	{tControllerName, tSerNum, tTrapText}
	STATUS	current
	DESCRIPTION	"Protection 2. level - EM(B) - insufficient - alarm disappeared"
::= { notifications 167775221 }

tEMBroBBrcInsufficientL2AlarmReset	NOTIFICATION-TYPE
	OBJECTS	{tControllerName, tSerNum, tTrapText}
	STATUS	current
	DESCRIPTION	"Protection 2. level - EM(B) - insufficient - alarm reset"
::= { notifications 167775222 }

tEMBroABrcMissingOrDamagedL1Activated	NOTIFICATION-TYPE
	OBJECTS	{tControllerName, tSerNum, tTrapText}
	STATUS	current
	DESCRIPTION	"Protection 1. level - EM(A) - missing or damaged - alarm activated"
::= { notifications 33557420 }

tEMBroABrcMissingOrDamagedL1Disappeared	NOTIFICATION-TYPE
	OBJECTS	{tControllerName, tSerNum, tTrapText}
	STATUS	current
	DESCRIPTION	"Protection 1. level - EM(A) - missing or damaged - alarm disappeared"
::= { notifications 33557421 }

tEMBroABrcMissingOrDamagedL1AlarmReset	NOTIFICATION-TYPE
	OBJECTS	{tControllerName, tSerNum, tTrapText}
	STATUS	current
	DESCRIPTION	"Protection 1. level - EM(A) - missing or damaged - alarm reset"
::= { notifications 33557422 }

tEMBroABrcMissingOrDamagedL2Activated	NOTIFICATION-TYPE
	OBJECTS	{tControllerName, tSerNum, tTrapText}
	STATUS	current
	DESCRIPTION	"Protection 2. level - EM(A) - missing or damaged - alarm activated"
::= { notifications 167775148 }

tEMBroABrcMissingOrDamagedL2Disappeared	NOTIFICATION-TYPE
	OBJECTS	{tControllerName, tSerNum, tTrapText}
	STATUS	current
	DESCRIPTION	"Protection 2. level - EM(A) - missing or damaged - alarm disappeared"
::= { notifications 167775149 }

tEMBroABrcMissingOrDamagedL2AlarmReset	NOTIFICATION-TYPE
	OBJECTS	{tControllerName, tSerNum, tTrapText}
	STATUS	current
	DESCRIPTION	"Protection 2. level - EM(A) - missing or damaged - alarm reset"
::= { notifications 167775150 }

tEMBroBBrcMissingOrDamagedL1Activated	NOTIFICATION-TYPE
	OBJECTS	{tControllerName, tSerNum, tTrapText}
	STATUS	current
	DESCRIPTION	"Protection 1. level - EM(B) - missing or damaged - alarm activated"
::= { notifications 33557444 }

tEMBroBBrcMissingOrDamagedL1Disappeared	NOTIFICATION-TYPE
	OBJECTS	{tControllerName, tSerNum, tTrapText}
	STATUS	current
	DESCRIPTION	"Protection 1. level - EM(B) - missing or damaged - alarm disappeared"
::= { notifications 33557445 }

tEMBroBBrcMissingOrDamagedL1AlarmReset	NOTIFICATION-TYPE
	OBJECTS	{tControllerName, tSerNum, tTrapText}
	STATUS	current
	DESCRIPTION	"Protection 1. level - EM(B) - missing or damaged - alarm reset"
::= { notifications 33557446 }

tEMBroBBrcMissingOrDamagedL2Activated	NOTIFICATION-TYPE
	OBJECTS	{tControllerName, tSerNum, tTrapText}
	STATUS	current
	DESCRIPTION	"Protection 2. level - EM(B) - missing or damaged - alarm activated"
::= { notifications 167775172 }

tEMBroBBrcMissingOrDamagedL2Disappeared	NOTIFICATION-TYPE
	OBJECTS	{tControllerName, tSerNum, tTrapText}
	STATUS	current
	DESCRIPTION	"Protection 2. level - EM(B) - missing or damaged - alarm disappeared"
::= { notifications 167775173 }

tEMBroBBrcMissingOrDamagedL2AlarmReset	NOTIFICATION-TYPE
	OBJECTS	{tControllerName, tSerNum, tTrapText}
	STATUS	current
	DESCRIPTION	"Protection 2. level - EM(B) - missing or damaged - alarm reset"
::= { notifications 167775174 }

tEventEMail1FailL1Activated	NOTIFICATION-TYPE
	OBJECTS	{tControllerName, tSerNum, tTrapText}
	STATUS	current
	DESCRIPTION	"Protection 1. level - Event e-mail 1 Fail - alarm activated"
::= { notifications 33557368 }

tEventEMail1FailL1Disappeared	NOTIFICATION-TYPE
	OBJECTS	{tControllerName, tSerNum, tTrapText}
	STATUS	current
	DESCRIPTION	"Protection 1. level - Event e-mail 1 Fail - alarm disappeared"
::= { notifications 33557369 }

tEventEMail1FailL1AlarmReset	NOTIFICATION-TYPE
	OBJECTS	{tControllerName, tSerNum, tTrapText}
	STATUS	current
	DESCRIPTION	"Protection 1. level - Event e-mail 1 Fail - alarm reset"
::= { notifications 33557370 }

tEventEMail2FailL1Activated	NOTIFICATION-TYPE
	OBJECTS	{tControllerName, tSerNum, tTrapText}
	STATUS	current
	DESCRIPTION	"Protection 1. level - Event e-mail 2 Fail - alarm activated"
::= { notifications 33557372 }

tEventEMail2FailL1Disappeared	NOTIFICATION-TYPE
	OBJECTS	{tControllerName, tSerNum, tTrapText}
	STATUS	current
	DESCRIPTION	"Protection 1. level - Event e-mail 2 Fail - alarm disappeared"
::= { notifications 33557373 }

tEventEMail2FailL1AlarmReset	NOTIFICATION-TYPE
	OBJECTS	{tControllerName, tSerNum, tTrapText}
	STATUS	current
	DESCRIPTION	"Protection 1. level - Event e-mail 2 Fail - alarm reset"
::= { notifications 33557374 }

tEventEMail3FailL1Activated	NOTIFICATION-TYPE
	OBJECTS	{tControllerName, tSerNum, tTrapText}
	STATUS	current
	DESCRIPTION	"Protection 1. level - Event e-mail 3 Fail - alarm activated"
::= { notifications 33557376 }

tEventEMail3FailL1Disappeared	NOTIFICATION-TYPE
	OBJECTS	{tControllerName, tSerNum, tTrapText}
	STATUS	current
	DESCRIPTION	"Protection 1. level - Event e-mail 3 Fail - alarm disappeared"
::= { notifications 33557377 }

tEventEMail3FailL1AlarmReset	NOTIFICATION-TYPE
	OBJECTS	{tControllerName, tSerNum, tTrapText}
	STATUS	current
	DESCRIPTION	"Protection 1. level - Event e-mail 3 Fail - alarm reset"
::= { notifications 33557378 }

tEventEMail4FailL1Activated	NOTIFICATION-TYPE
	OBJECTS	{tControllerName, tSerNum, tTrapText}
	STATUS	current
	DESCRIPTION	"Protection 1. level - Event e-mail 4 Fail - alarm activated"
::= { notifications 33557380 }

tEventEMail4FailL1Disappeared	NOTIFICATION-TYPE
	OBJECTS	{tControllerName, tSerNum, tTrapText}
	STATUS	current
	DESCRIPTION	"Protection 1. level - Event e-mail 4 Fail - alarm disappeared"
::= { notifications 33557381 }

tEventEMail4FailL1AlarmReset	NOTIFICATION-TYPE
	OBJECTS	{tControllerName, tSerNum, tTrapText}
	STATUS	current
	DESCRIPTION	"Protection 1. level - Event e-mail 4 Fail - alarm reset"
::= { notifications 33557382 }

tEventSMS1FailL1Activated	NOTIFICATION-TYPE
	OBJECTS	{tControllerName, tSerNum, tTrapText}
	STATUS	current
	DESCRIPTION	"Protection 1. level - Event SMS 1 Fail - alarm activated"
::= { notifications 33557384 }

tEventSMS1FailL1Disappeared	NOTIFICATION-TYPE
	OBJECTS	{tControllerName, tSerNum, tTrapText}
	STATUS	current
	DESCRIPTION	"Protection 1. level - Event SMS 1 Fail - alarm disappeared"
::= { notifications 33557385 }

tEventSMS1FailL1AlarmReset	NOTIFICATION-TYPE
	OBJECTS	{tControllerName, tSerNum, tTrapText}
	STATUS	current
	DESCRIPTION	"Protection 1. level - Event SMS 1 Fail - alarm reset"
::= { notifications 33557386 }

tEventSMS2FailL1Activated	NOTIFICATION-TYPE
	OBJECTS	{tControllerName, tSerNum, tTrapText}
	STATUS	current
	DESCRIPTION	"Protection 1. level - Event SMS 2 Fail - alarm activated"
::= { notifications 33557388 }

tEventSMS2FailL1Disappeared	NOTIFICATION-TYPE
	OBJECTS	{tControllerName, tSerNum, tTrapText}
	STATUS	current
	DESCRIPTION	"Protection 1. level - Event SMS 2 Fail - alarm disappeared"
::= { notifications 33557389 }

tEventSMS2FailL1AlarmReset	NOTIFICATION-TYPE
	OBJECTS	{tControllerName, tSerNum, tTrapText}
	STATUS	current
	DESCRIPTION	"Protection 1. level - Event SMS 2 Fail - alarm reset"
::= { notifications 33557390 }

tEventSMS3FailL1Activated	NOTIFICATION-TYPE
	OBJECTS	{tControllerName, tSerNum, tTrapText}
	STATUS	current
	DESCRIPTION	"Protection 1. level - Event SMS 3 Fail - alarm activated"
::= { notifications 33557392 }

tEventSMS3FailL1Disappeared	NOTIFICATION-TYPE
	OBJECTS	{tControllerName, tSerNum, tTrapText}
	STATUS	current
	DESCRIPTION	"Protection 1. level - Event SMS 3 Fail - alarm disappeared"
::= { notifications 33557393 }

tEventSMS3FailL1AlarmReset	NOTIFICATION-TYPE
	OBJECTS	{tControllerName, tSerNum, tTrapText}
	STATUS	current
	DESCRIPTION	"Protection 1. level - Event SMS 3 Fail - alarm reset"
::= { notifications 33557394 }

tEventSMS4FailL1Activated	NOTIFICATION-TYPE
	OBJECTS	{tControllerName, tSerNum, tTrapText}
	STATUS	current
	DESCRIPTION	"Protection 1. level - Event SMS 4 Fail - alarm activated"
::= { notifications 33557396 }

tEventSMS4FailL1Disappeared	NOTIFICATION-TYPE
	OBJECTS	{tControllerName, tSerNum, tTrapText}
	STATUS	current
	DESCRIPTION	"Protection 1. level - Event SMS 4 Fail - alarm disappeared"
::= { notifications 33557397 }

tEventSMS4FailL1AlarmReset	NOTIFICATION-TYPE
	OBJECTS	{tControllerName, tSerNum, tTrapText}
	STATUS	current
	DESCRIPTION	"Protection 1. level - Event SMS 4 Fail - alarm reset"
::= { notifications 33557398 }

tAlarmEMail1FailL1Activated	NOTIFICATION-TYPE
	OBJECTS	{tControllerName, tSerNum, tTrapText}
	STATUS	current
	DESCRIPTION	"Protection 1. level - Alarm e-mail 1 Fail - alarm activated"
::= { notifications 33557692 }

tAlarmEMail1FailL1Disappeared	NOTIFICATION-TYPE
	OBJECTS	{tControllerName, tSerNum, tTrapText}
	STATUS	current
	DESCRIPTION	"Protection 1. level - Alarm e-mail 1 Fail - alarm disappeared"
::= { notifications 33557693 }

tAlarmEMail1FailL1AlarmReset	NOTIFICATION-TYPE
	OBJECTS	{tControllerName, tSerNum, tTrapText}
	STATUS	current
	DESCRIPTION	"Protection 1. level - Alarm e-mail 1 Fail - alarm reset"
::= { notifications 33557694 }

tAlarmEMail2FailL1Activated	NOTIFICATION-TYPE
	OBJECTS	{tControllerName, tSerNum, tTrapText}
	STATUS	current
	DESCRIPTION	"Protection 1. level - Alarm e-mail 2 Fail - alarm activated"
::= { notifications 33557696 }

tAlarmEMail2FailL1Disappeared	NOTIFICATION-TYPE
	OBJECTS	{tControllerName, tSerNum, tTrapText}
	STATUS	current
	DESCRIPTION	"Protection 1. level - Alarm e-mail 2 Fail - alarm disappeared"
::= { notifications 33557697 }

tAlarmEMail2FailL1AlarmReset	NOTIFICATION-TYPE
	OBJECTS	{tControllerName, tSerNum, tTrapText}
	STATUS	current
	DESCRIPTION	"Protection 1. level - Alarm e-mail 2 Fail - alarm reset"
::= { notifications 33557698 }

tAlarmEMail3FailL1Activated	NOTIFICATION-TYPE
	OBJECTS	{tControllerName, tSerNum, tTrapText}
	STATUS	current
	DESCRIPTION	"Protection 1. level - Alarm e-mail 3 Fail - alarm activated"
::= { notifications 33557700 }

tAlarmEMail3FailL1Disappeared	NOTIFICATION-TYPE
	OBJECTS	{tControllerName, tSerNum, tTrapText}
	STATUS	current
	DESCRIPTION	"Protection 1. level - Alarm e-mail 3 Fail - alarm disappeared"
::= { notifications 33557701 }

tAlarmEMail3FailL1AlarmReset	NOTIFICATION-TYPE
	OBJECTS	{tControllerName, tSerNum, tTrapText}
	STATUS	current
	DESCRIPTION	"Protection 1. level - Alarm e-mail 3 Fail - alarm reset"
::= { notifications 33557702 }

tAlarmEMail4FailL1Activated	NOTIFICATION-TYPE
	OBJECTS	{tControllerName, tSerNum, tTrapText}
	STATUS	current
	DESCRIPTION	"Protection 1. level - Alarm e-mail 4 Fail - alarm activated"
::= { notifications 33557704 }

tAlarmEMail4FailL1Disappeared	NOTIFICATION-TYPE
	OBJECTS	{tControllerName, tSerNum, tTrapText}
	STATUS	current
	DESCRIPTION	"Protection 1. level - Alarm e-mail 4 Fail - alarm disappeared"
::= { notifications 33557705 }

tAlarmEMail4FailL1AlarmReset	NOTIFICATION-TYPE
	OBJECTS	{tControllerName, tSerNum, tTrapText}
	STATUS	current
	DESCRIPTION	"Protection 1. level - Alarm e-mail 4 Fail - alarm reset"
::= { notifications 33557706 }

tAlarmSMS1FailL1Activated	NOTIFICATION-TYPE
	OBJECTS	{tControllerName, tSerNum, tTrapText}
	STATUS	current
	DESCRIPTION	"Protection 1. level - Alarm SMS 1 Fail - alarm activated"
::= { notifications 33557708 }

tAlarmSMS1FailL1Disappeared	NOTIFICATION-TYPE
	OBJECTS	{tControllerName, tSerNum, tTrapText}
	STATUS	current
	DESCRIPTION	"Protection 1. level - Alarm SMS 1 Fail - alarm disappeared"
::= { notifications 33557709 }

tAlarmSMS1FailL1AlarmReset	NOTIFICATION-TYPE
	OBJECTS	{tControllerName, tSerNum, tTrapText}
	STATUS	current
	DESCRIPTION	"Protection 1. level - Alarm SMS 1 Fail - alarm reset"
::= { notifications 33557710 }

tAlarmSMS2FailL1Activated	NOTIFICATION-TYPE
	OBJECTS	{tControllerName, tSerNum, tTrapText}
	STATUS	current
	DESCRIPTION	"Protection 1. level - Alarm SMS 2 Fail - alarm activated"
::= { notifications 33557712 }

tAlarmSMS2FailL1Disappeared	NOTIFICATION-TYPE
	OBJECTS	{tControllerName, tSerNum, tTrapText}
	STATUS	current
	DESCRIPTION	"Protection 1. level - Alarm SMS 2 Fail - alarm disappeared"
::= { notifications 33557713 }

tAlarmSMS2FailL1AlarmReset	NOTIFICATION-TYPE
	OBJECTS	{tControllerName, tSerNum, tTrapText}
	STATUS	current
	DESCRIPTION	"Protection 1. level - Alarm SMS 2 Fail - alarm reset"
::= { notifications 33557714 }

tAlarmSMS3FailL1Activated	NOTIFICATION-TYPE
	OBJECTS	{tControllerName, tSerNum, tTrapText}
	STATUS	current
	DESCRIPTION	"Protection 1. level - Alarm SMS 3 Fail - alarm activated"
::= { notifications 33557716 }

tAlarmSMS3FailL1Disappeared	NOTIFICATION-TYPE
	OBJECTS	{tControllerName, tSerNum, tTrapText}
	STATUS	current
	DESCRIPTION	"Protection 1. level - Alarm SMS 3 Fail - alarm disappeared"
::= { notifications 33557717 }

tAlarmSMS3FailL1AlarmReset	NOTIFICATION-TYPE
	OBJECTS	{tControllerName, tSerNum, tTrapText}
	STATUS	current
	DESCRIPTION	"Protection 1. level - Alarm SMS 3 Fail - alarm reset"
::= { notifications 33557718 }

tAlarmSMS4FailL1Activated	NOTIFICATION-TYPE
	OBJECTS	{tControllerName, tSerNum, tTrapText}
	STATUS	current
	DESCRIPTION	"Protection 1. level - Alarm SMS 4 Fail - alarm activated"
::= { notifications 33557720 }

tAlarmSMS4FailL1Disappeared	NOTIFICATION-TYPE
	OBJECTS	{tControllerName, tSerNum, tTrapText}
	STATUS	current
	DESCRIPTION	"Protection 1. level - Alarm SMS 4 Fail - alarm disappeared"
::= { notifications 33557721 }

tAlarmSMS4FailL1AlarmReset	NOTIFICATION-TYPE
	OBJECTS	{tControllerName, tSerNum, tTrapText}
	STATUS	current
	DESCRIPTION	"Protection 1. level - Alarm SMS 4 Fail - alarm reset"
::= { notifications 33557722 }

tSNMPTRAP1FailL1Activated	NOTIFICATION-TYPE
	OBJECTS	{tControllerName, tSerNum, tTrapText}
	STATUS	current
	DESCRIPTION	"Protection 1. level - SNMP TRAP 1 Fail - alarm activated"
::= { notifications 33557724 }

tSNMPTRAP1FailL1Disappeared	NOTIFICATION-TYPE
	OBJECTS	{tControllerName, tSerNum, tTrapText}
	STATUS	current
	DESCRIPTION	"Protection 1. level - SNMP TRAP 1 Fail - alarm disappeared"
::= { notifications 33557725 }

tSNMPTRAP1FailL1AlarmReset	NOTIFICATION-TYPE
	OBJECTS	{tControllerName, tSerNum, tTrapText}
	STATUS	current
	DESCRIPTION	"Protection 1. level - SNMP TRAP 1 Fail - alarm reset"
::= { notifications 33557726 }

tSNMPTRAP2FailL1Activated	NOTIFICATION-TYPE
	OBJECTS	{tControllerName, tSerNum, tTrapText}
	STATUS	current
	DESCRIPTION	"Protection 1. level - SNMP TRAP 2 Fail - alarm activated"
::= { notifications 33557728 }

tSNMPTRAP2FailL1Disappeared	NOTIFICATION-TYPE
	OBJECTS	{tControllerName, tSerNum, tTrapText}
	STATUS	current
	DESCRIPTION	"Protection 1. level - SNMP TRAP 2 Fail - alarm disappeared"
::= { notifications 33557729 }

tSNMPTRAP2FailL1AlarmReset	NOTIFICATION-TYPE
	OBJECTS	{tControllerName, tSerNum, tTrapText}
	STATUS	current
	DESCRIPTION	"Protection 1. level - SNMP TRAP 2 Fail - alarm reset"
::= { notifications 33557730 }

tECUDiagBlockedL1Activated	NOTIFICATION-TYPE
	OBJECTS	{tControllerName, tSerNum, tTrapText}
	STATUS	current
	DESCRIPTION	"Protection 1. level - ECUDiagBlocked - alarm activated"
::= { notifications 33554592 }

tECUDiagBlockedL1Disappeared	NOTIFICATION-TYPE
	OBJECTS	{tControllerName, tSerNum, tTrapText}
	STATUS	current
	DESCRIPTION	"Protection 1. level - ECUDiagBlocked - alarm disappeared"
::= { notifications 33554593 }

tECUDiagBlockedL1AlarmReset	NOTIFICATION-TYPE
	OBJECTS	{tControllerName, tSerNum, tTrapText}
	STATUS	current
	DESCRIPTION	"Protection 1. level - ECUDiagBlocked - alarm reset"
::= { notifications 33554594 }

tWrongPLCConfigurationL1Activated	NOTIFICATION-TYPE
	OBJECTS	{tControllerName, tSerNum, tTrapText}
	STATUS	current
	DESCRIPTION	"Protection 1. level - Wrong PLC Configuration - alarm activated"
::= { notifications 33554596 }

tWrongPLCConfigurationL1Disappeared	NOTIFICATION-TYPE
	OBJECTS	{tControllerName, tSerNum, tTrapText}
	STATUS	current
	DESCRIPTION	"Protection 1. level - Wrong PLC Configuration - alarm disappeared"
::= { notifications 33554597 }

tWrongPLCConfigurationL1AlarmReset	NOTIFICATION-TYPE
	OBJECTS	{tControllerName, tSerNum, tTrapText}
	STATUS	current
	DESCRIPTION	"Protection 1. level - Wrong PLC Configuration - alarm reset"
::= { notifications 33554598 }

tRTCBatteryFlatL1Activated	NOTIFICATION-TYPE
	OBJECTS	{tControllerName, tSerNum, tTrapText}
	STATUS	current
	DESCRIPTION	"Protection 1. level - RTC Battery Flat - alarm activated"
::= { notifications 33554600 }

tRTCBatteryFlatL1Disappeared	NOTIFICATION-TYPE
	OBJECTS	{tControllerName, tSerNum, tTrapText}
	STATUS	current
	DESCRIPTION	"Protection 1. level - RTC Battery Flat - alarm disappeared"
::= { notifications 33554601 }

tRTCBatteryFlatL1AlarmReset	NOTIFICATION-TYPE
	OBJECTS	{tControllerName, tSerNum, tTrapText}
	STATUS	current
	DESCRIPTION	"Protection 1. level - RTC Battery Flat - alarm reset"
::= { notifications 33554602 }

tPasswEnterBlockL1Activated	NOTIFICATION-TYPE
	OBJECTS	{tControllerName, tSerNum, tTrapText}
	STATUS	current
	DESCRIPTION	"Protection 1. level - PasswEnterBlock - alarm activated"
::= { notifications 33558652 }

tPasswEnterBlockL1Disappeared	NOTIFICATION-TYPE
	OBJECTS	{tControllerName, tSerNum, tTrapText}
	STATUS	current
	DESCRIPTION	"Protection 1. level - PasswEnterBlock - alarm disappeared"
::= { notifications 33558653 }

tPasswEnterBlockL1AlarmReset	NOTIFICATION-TYPE
	OBJECTS	{tControllerName, tSerNum, tTrapText}
	STATUS	current
	DESCRIPTION	"Protection 1. level - PasswEnterBlock - alarm reset"
::= { notifications 33558654 }

tControllerRestartRequiredL1Activated	NOTIFICATION-TYPE
	OBJECTS	{tControllerName, tSerNum, tTrapText}
	STATUS	current
	DESCRIPTION	"Protection 1. level - Controller Restart Required - alarm activated"
::= { notifications 33565120 }

tControllerRestartRequiredL1Disappeared	NOTIFICATION-TYPE
	OBJECTS	{tControllerName, tSerNum, tTrapText}
	STATUS	current
	DESCRIPTION	"Protection 1. level - Controller Restart Required - alarm disappeared"
::= { notifications 33565121 }

tControllerRestartRequiredL1AlarmReset	NOTIFICATION-TYPE
	OBJECTS	{tControllerName, tSerNum, tTrapText}
	STATUS	current
	DESCRIPTION	"Protection 1. level - Controller Restart Required - alarm reset"
::= { notifications 33565122 }

tHuaweiSUN20002CommFailL1Activated	NOTIFICATION-TYPE
	OBJECTS	{tControllerName, tSerNum, tTrapText}
	STATUS	current
	DESCRIPTION	"Protection 1. level - Huawei SUN2000 2 Comm Fail - alarm activated"
::= { notifications 33558212 }

tHuaweiSUN20002CommFailL1Disappeared	NOTIFICATION-TYPE
	OBJECTS	{tControllerName, tSerNum, tTrapText}
	STATUS	current
	DESCRIPTION	"Protection 1. level - Huawei SUN2000 2 Comm Fail - alarm disappeared"
::= { notifications 33558213 }

tHuaweiSUN20002CommFailL1AlarmReset	NOTIFICATION-TYPE
	OBJECTS	{tControllerName, tSerNum, tTrapText}
	STATUS	current
	DESCRIPTION	"Protection 1. level - Huawei SUN2000 2 Comm Fail - alarm reset"
::= { notifications 33558214 }

tHuaweiSUN20002CommFailL2Activated	NOTIFICATION-TYPE
	OBJECTS	{tControllerName, tSerNum, tTrapText}
	STATUS	current
	DESCRIPTION	"Protection 2. level - Huawei SUN2000 2 Comm Fail - alarm activated"
::= { notifications 167775940 }

tHuaweiSUN20002CommFailL2Disappeared	NOTIFICATION-TYPE
	OBJECTS	{tControllerName, tSerNum, tTrapText}
	STATUS	current
	DESCRIPTION	"Protection 2. level - Huawei SUN2000 2 Comm Fail - alarm disappeared"
::= { notifications 167775941 }

tHuaweiSUN20002CommFailL2AlarmReset	NOTIFICATION-TYPE
	OBJECTS	{tControllerName, tSerNum, tTrapText}
	STATUS	current
	DESCRIPTION	"Protection 2. level - Huawei SUN2000 2 Comm Fail - alarm reset"
::= { notifications 167775942 }

tSOLAXX3110KCommFailL1Activated	NOTIFICATION-TYPE
	OBJECTS	{tControllerName, tSerNum, tTrapText}
	STATUS	current
	DESCRIPTION	"Protection 1. level - SOLAX X3-110K Comm Fail - alarm activated"
::= { notifications 33558216 }

tSOLAXX3110KCommFailL1Disappeared	NOTIFICATION-TYPE
	OBJECTS	{tControllerName, tSerNum, tTrapText}
	STATUS	current
	DESCRIPTION	"Protection 1. level - SOLAX X3-110K Comm Fail - alarm disappeared"
::= { notifications 33558217 }

tSOLAXX3110KCommFailL1AlarmReset	NOTIFICATION-TYPE
	OBJECTS	{tControllerName, tSerNum, tTrapText}
	STATUS	current
	DESCRIPTION	"Protection 1. level - SOLAX X3-110K Comm Fail - alarm reset"
::= { notifications 33558218 }

tSOLAXX3110KCommFailL2Activated	NOTIFICATION-TYPE
	OBJECTS	{tControllerName, tSerNum, tTrapText}
	STATUS	current
	DESCRIPTION	"Protection 2. level - SOLAX X3-110K Comm Fail - alarm activated"
::= { notifications 167775944 }

tSOLAXX3110KCommFailL2Disappeared	NOTIFICATION-TYPE
	OBJECTS	{tControllerName, tSerNum, tTrapText}
	STATUS	current
	DESCRIPTION	"Protection 2. level - SOLAX X3-110K Comm Fail - alarm disappeared"
::= { notifications 167775945 }

tSOLAXX3110KCommFailL2AlarmReset	NOTIFICATION-TYPE
	OBJECTS	{tControllerName, tSerNum, tTrapText}
	STATUS	current
	DESCRIPTION	"Protection 2. level - SOLAX X3-110K Comm Fail - alarm reset"
::= { notifications 167775946 }

tM4MCommFailL1Activated	NOTIFICATION-TYPE
	OBJECTS	{tControllerName, tSerNum, tTrapText}
	STATUS	current
	DESCRIPTION	"Protection 1. level - M4M Comm Fail - alarm activated"
::= { notifications 33558220 }

tM4MCommFailL1Disappeared	NOTIFICATION-TYPE
	OBJECTS	{tControllerName, tSerNum, tTrapText}
	STATUS	current
	DESCRIPTION	"Protection 1. level - M4M Comm Fail - alarm disappeared"
::= { notifications 33558221 }

tM4MCommFailL1AlarmReset	NOTIFICATION-TYPE
	OBJECTS	{tControllerName, tSerNum, tTrapText}
	STATUS	current
	DESCRIPTION	"Protection 1. level - M4M Comm Fail - alarm reset"
::= { notifications 33558222 }

tM4MCommFailL2Activated	NOTIFICATION-TYPE
	OBJECTS	{tControllerName, tSerNum, tTrapText}
	STATUS	current
	DESCRIPTION	"Protection 2. level - M4M Comm Fail - alarm activated"
::= { notifications 167775948 }

tM4MCommFailL2Disappeared	NOTIFICATION-TYPE
	OBJECTS	{tControllerName, tSerNum, tTrapText}
	STATUS	current
	DESCRIPTION	"Protection 2. level - M4M Comm Fail - alarm disappeared"
::= { notifications 167775949 }

tM4MCommFailL2AlarmReset	NOTIFICATION-TYPE
	OBJECTS	{tControllerName, tSerNum, tTrapText}
	STATUS	current
	DESCRIPTION	"Protection 2. level - M4M Comm Fail - alarm reset"
::= { notifications 167775950 }

tSinexcelPWS1CommFailL1Activated	NOTIFICATION-TYPE
	OBJECTS	{tControllerName, tSerNum, tTrapText}
	STATUS	current
	DESCRIPTION	"Protection 1. level - Sinexcel PWS1  Comm Fail - alarm activated"
::= { notifications 33558224 }

tSinexcelPWS1CommFailL1Disappeared	NOTIFICATION-TYPE
	OBJECTS	{tControllerName, tSerNum, tTrapText}
	STATUS	current
	DESCRIPTION	"Protection 1. level - Sinexcel PWS1  Comm Fail - alarm disappeared"
::= { notifications 33558225 }

tSinexcelPWS1CommFailL1AlarmReset	NOTIFICATION-TYPE
	OBJECTS	{tControllerName, tSerNum, tTrapText}
	STATUS	current
	DESCRIPTION	"Protection 1. level - Sinexcel PWS1  Comm Fail - alarm reset"
::= { notifications 33558226 }

tSinexcelPWS1CommFailL2Activated	NOTIFICATION-TYPE
	OBJECTS	{tControllerName, tSerNum, tTrapText}
	STATUS	current
	DESCRIPTION	"Protection 2. level - Sinexcel PWS1  Comm Fail - alarm activated"
::= { notifications 167775952 }

tSinexcelPWS1CommFailL2Disappeared	NOTIFICATION-TYPE
	OBJECTS	{tControllerName, tSerNum, tTrapText}
	STATUS	current
	DESCRIPTION	"Protection 2. level - Sinexcel PWS1  Comm Fail - alarm disappeared"
::= { notifications 167775953 }

tSinexcelPWS1CommFailL2AlarmReset	NOTIFICATION-TYPE
	OBJECTS	{tControllerName, tSerNum, tTrapText}
	STATUS	current
	DESCRIPTION	"Protection 2. level - Sinexcel PWS1  Comm Fail - alarm reset"
::= { notifications 167775954 }

tRBMSCommFailL1Activated	NOTIFICATION-TYPE
	OBJECTS	{tControllerName, tSerNum, tTrapText}
	STATUS	current
	DESCRIPTION	"Protection 1. level - RBMS Comm Fail - alarm activated"
::= { notifications 33558228 }

tRBMSCommFailL1Disappeared	NOTIFICATION-TYPE
	OBJECTS	{tControllerName, tSerNum, tTrapText}
	STATUS	current
	DESCRIPTION	"Protection 1. level - RBMS Comm Fail - alarm disappeared"
::= { notifications 33558229 }

tRBMSCommFailL1AlarmReset	NOTIFICATION-TYPE
	OBJECTS	{tControllerName, tSerNum, tTrapText}
	STATUS	current
	DESCRIPTION	"Protection 1. level - RBMS Comm Fail - alarm reset"
::= { notifications 33558230 }

tRBMSCommFailL2Activated	NOTIFICATION-TYPE
	OBJECTS	{tControllerName, tSerNum, tTrapText}
	STATUS	current
	DESCRIPTION	"Protection 2. level - RBMS Comm Fail - alarm activated"
::= { notifications 167775956 }

tRBMSCommFailL2Disappeared	NOTIFICATION-TYPE
	OBJECTS	{tControllerName, tSerNum, tTrapText}
	STATUS	current
	DESCRIPTION	"Protection 2. level - RBMS Comm Fail - alarm disappeared"
::= { notifications 167775957 }

tRBMSCommFailL2AlarmReset	NOTIFICATION-TYPE
	OBJECTS	{tControllerName, tSerNum, tTrapText}
	STATUS	current
	DESCRIPTION	"Protection 2. level - RBMS Comm Fail - alarm reset"
::= { notifications 167775958 }

tECU6CommFailL1Activated	NOTIFICATION-TYPE
	OBJECTS	{tControllerName, tSerNum, tTrapText}
	STATUS	current
	DESCRIPTION	"Protection 1. level - ECU 6 Comm Fail - alarm activated"
::= { notifications 33558232 }

tECU6CommFailL1Disappeared	NOTIFICATION-TYPE
	OBJECTS	{tControllerName, tSerNum, tTrapText}
	STATUS	current
	DESCRIPTION	"Protection 1. level - ECU 6 Comm Fail - alarm disappeared"
::= { notifications 33558233 }

tECU6CommFailL1AlarmReset	NOTIFICATION-TYPE
	OBJECTS	{tControllerName, tSerNum, tTrapText}
	STATUS	current
	DESCRIPTION	"Protection 1. level - ECU 6 Comm Fail - alarm reset"
::= { notifications 33558234 }

tECU6CommFailL2Activated	NOTIFICATION-TYPE
	OBJECTS	{tControllerName, tSerNum, tTrapText}
	STATUS	current
	DESCRIPTION	"Protection 2. level - ECU 6 Comm Fail - alarm activated"
::= { notifications 167775960 }

tECU6CommFailL2Disappeared	NOTIFICATION-TYPE
	OBJECTS	{tControllerName, tSerNum, tTrapText}
	STATUS	current
	DESCRIPTION	"Protection 2. level - ECU 6 Comm Fail - alarm disappeared"
::= { notifications 167775961 }

tECU6CommFailL2AlarmReset	NOTIFICATION-TYPE
	OBJECTS	{tControllerName, tSerNum, tTrapText}
	STATUS	current
	DESCRIPTION	"Protection 2. level - ECU 6 Comm Fail - alarm reset"
::= { notifications 167775962 }

tECU7CommFailL1Activated	NOTIFICATION-TYPE
	OBJECTS	{tControllerName, tSerNum, tTrapText}
	STATUS	current
	DESCRIPTION	"Protection 1. level - ECU 7 Comm Fail - alarm activated"
::= { notifications 33558236 }

tECU7CommFailL1Disappeared	NOTIFICATION-TYPE
	OBJECTS	{tControllerName, tSerNum, tTrapText}
	STATUS	current
	DESCRIPTION	"Protection 1. level - ECU 7 Comm Fail - alarm disappeared"
::= { notifications 33558237 }

tECU7CommFailL1AlarmReset	NOTIFICATION-TYPE
	OBJECTS	{tControllerName, tSerNum, tTrapText}
	STATUS	current
	DESCRIPTION	"Protection 1. level - ECU 7 Comm Fail - alarm reset"
::= { notifications 33558238 }

tECU7CommFailL2Activated	NOTIFICATION-TYPE
	OBJECTS	{tControllerName, tSerNum, tTrapText}
	STATUS	current
	DESCRIPTION	"Protection 2. level - ECU 7 Comm Fail - alarm activated"
::= { notifications 167775964 }

tECU7CommFailL2Disappeared	NOTIFICATION-TYPE
	OBJECTS	{tControllerName, tSerNum, tTrapText}
	STATUS	current
	DESCRIPTION	"Protection 2. level - ECU 7 Comm Fail - alarm disappeared"
::= { notifications 167775965 }

tECU7CommFailL2AlarmReset	NOTIFICATION-TYPE
	OBJECTS	{tControllerName, tSerNum, tTrapText}
	STATUS	current
	DESCRIPTION	"Protection 2. level - ECU 7 Comm Fail - alarm reset"
::= { notifications 167775966 }

tECU8CommFailL1Activated	NOTIFICATION-TYPE
	OBJECTS	{tControllerName, tSerNum, tTrapText}
	STATUS	current
	DESCRIPTION	"Protection 1. level - ECU 8 Comm Fail - alarm activated"
::= { notifications 33558240 }

tECU8CommFailL1Disappeared	NOTIFICATION-TYPE
	OBJECTS	{tControllerName, tSerNum, tTrapText}
	STATUS	current
	DESCRIPTION	"Protection 1. level - ECU 8 Comm Fail - alarm disappeared"
::= { notifications 33558241 }

tECU8CommFailL1AlarmReset	NOTIFICATION-TYPE
	OBJECTS	{tControllerName, tSerNum, tTrapText}
	STATUS	current
	DESCRIPTION	"Protection 1. level - ECU 8 Comm Fail - alarm reset"
::= { notifications 33558242 }

tECU8CommFailL2Activated	NOTIFICATION-TYPE
	OBJECTS	{tControllerName, tSerNum, tTrapText}
	STATUS	current
	DESCRIPTION	"Protection 2. level - ECU 8 Comm Fail - alarm activated"
::= { notifications 167775968 }

tECU8CommFailL2Disappeared	NOTIFICATION-TYPE
	OBJECTS	{tControllerName, tSerNum, tTrapText}
	STATUS	current
	DESCRIPTION	"Protection 2. level - ECU 8 Comm Fail - alarm disappeared"
::= { notifications 167775969 }

tECU8CommFailL2AlarmReset	NOTIFICATION-TYPE
	OBJECTS	{tControllerName, tSerNum, tTrapText}
	STATUS	current
	DESCRIPTION	"Protection 2. level - ECU 8 Comm Fail - alarm reset"
::= { notifications 167775970 }

tECU9CommFailL1Activated	NOTIFICATION-TYPE
	OBJECTS	{tControllerName, tSerNum, tTrapText}
	STATUS	current
	DESCRIPTION	"Protection 1. level - ECU 9 Comm Fail - alarm activated"
::= { notifications 33558244 }

tECU9CommFailL1Disappeared	NOTIFICATION-TYPE
	OBJECTS	{tControllerName, tSerNum, tTrapText}
	STATUS	current
	DESCRIPTION	"Protection 1. level - ECU 9 Comm Fail - alarm disappeared"
::= { notifications 33558245 }

tECU9CommFailL1AlarmReset	NOTIFICATION-TYPE
	OBJECTS	{tControllerName, tSerNum, tTrapText}
	STATUS	current
	DESCRIPTION	"Protection 1. level - ECU 9 Comm Fail - alarm reset"
::= { notifications 33558246 }

tECU9CommFailL2Activated	NOTIFICATION-TYPE
	OBJECTS	{tControllerName, tSerNum, tTrapText}
	STATUS	current
	DESCRIPTION	"Protection 2. level - ECU 9 Comm Fail - alarm activated"
::= { notifications 167775972 }

tECU9CommFailL2Disappeared	NOTIFICATION-TYPE
	OBJECTS	{tControllerName, tSerNum, tTrapText}
	STATUS	current
	DESCRIPTION	"Protection 2. level - ECU 9 Comm Fail - alarm disappeared"
::= { notifications 167775973 }

tECU9CommFailL2AlarmReset	NOTIFICATION-TYPE
	OBJECTS	{tControllerName, tSerNum, tTrapText}
	STATUS	current
	DESCRIPTION	"Protection 2. level - ECU 9 Comm Fail - alarm reset"
::= { notifications 167775974 }

tresL1Activated1	NOTIFICATION-TYPE
	OBJECTS	{tControllerName, tSerNum, tTrapText}
	STATUS	current
	DESCRIPTION	"Protection 1. level - res - alarm activated"
::= { notifications 33558248 }

tresL1Disappeared1	NOTIFICATION-TYPE
	OBJECTS	{tControllerName, tSerNum, tTrapText}
	STATUS	current
	DESCRIPTION	"Protection 1. level - res - alarm disappeared"
::= { notifications 33558249 }

tresL1AlarmReset1	NOTIFICATION-TYPE
	OBJECTS	{tControllerName, tSerNum, tTrapText}
	STATUS	current
	DESCRIPTION	"Protection 1. level - res - alarm reset"
::= { notifications 33558250 }

tresL2Activated1	NOTIFICATION-TYPE
	OBJECTS	{tControllerName, tSerNum, tTrapText}
	STATUS	current
	DESCRIPTION	"Protection 2. level - res - alarm activated"
::= { notifications 167775976 }

tresL2Disappeared1	NOTIFICATION-TYPE
	OBJECTS	{tControllerName, tSerNum, tTrapText}
	STATUS	current
	DESCRIPTION	"Protection 2. level - res - alarm disappeared"
::= { notifications 167775977 }

tresL2AlarmReset1	NOTIFICATION-TYPE
	OBJECTS	{tControllerName, tSerNum, tTrapText}
	STATUS	current
	DESCRIPTION	"Protection 2. level - res - alarm reset"
::= { notifications 167775978 }

tresSFActivated1	NOTIFICATION-TYPE
	OBJECTS	{tControllerName, tSerNum, tTrapText}
	STATUS	current
	DESCRIPTION	"Protection Sensor Fail - res - alarm activated"
::= { notifications 301993704 }

tresSFDisappeared1	NOTIFICATION-TYPE
	OBJECTS	{tControllerName, tSerNum, tTrapText}
	STATUS	current
	DESCRIPTION	"Protection Sensor Fail - res - alarm disappeared"
::= { notifications 301993705 }

tresSFAlarmReset1	NOTIFICATION-TYPE
	OBJECTS	{tControllerName, tSerNum, tTrapText}
	STATUS	current
	DESCRIPTION	"Protection Sensor Fail - res - alarm reset"
::= { notifications 301993706 }

tresL1Activated2	NOTIFICATION-TYPE
	OBJECTS	{tControllerName, tSerNum, tTrapText}
	STATUS	current
	DESCRIPTION	"Protection 1. level - res - alarm activated"
::= { notifications 33558252 }

tresL1Disappeared2	NOTIFICATION-TYPE
	OBJECTS	{tControllerName, tSerNum, tTrapText}
	STATUS	current
	DESCRIPTION	"Protection 1. level - res - alarm disappeared"
::= { notifications 33558253 }

tresL1AlarmReset2	NOTIFICATION-TYPE
	OBJECTS	{tControllerName, tSerNum, tTrapText}
	STATUS	current
	DESCRIPTION	"Protection 1. level - res - alarm reset"
::= { notifications 33558254 }

tresL2Activated2	NOTIFICATION-TYPE
	OBJECTS	{tControllerName, tSerNum, tTrapText}
	STATUS	current
	DESCRIPTION	"Protection 2. level - res - alarm activated"
::= { notifications 167775980 }

tresL2Disappeared2	NOTIFICATION-TYPE
	OBJECTS	{tControllerName, tSerNum, tTrapText}
	STATUS	current
	DESCRIPTION	"Protection 2. level - res - alarm disappeared"
::= { notifications 167775981 }

tresL2AlarmReset2	NOTIFICATION-TYPE
	OBJECTS	{tControllerName, tSerNum, tTrapText}
	STATUS	current
	DESCRIPTION	"Protection 2. level - res - alarm reset"
::= { notifications 167775982 }

tresSFActivated2	NOTIFICATION-TYPE
	OBJECTS	{tControllerName, tSerNum, tTrapText}
	STATUS	current
	DESCRIPTION	"Protection Sensor Fail - res - alarm activated"
::= { notifications 301993708 }

tresSFDisappeared2	NOTIFICATION-TYPE
	OBJECTS	{tControllerName, tSerNum, tTrapText}
	STATUS	current
	DESCRIPTION	"Protection Sensor Fail - res - alarm disappeared"
::= { notifications 301993709 }

tresSFAlarmReset2	NOTIFICATION-TYPE
	OBJECTS	{tControllerName, tSerNum, tTrapText}
	STATUS	current
	DESCRIPTION	"Protection Sensor Fail - res - alarm reset"
::= { notifications 301993710 }

tresL1Activated3	NOTIFICATION-TYPE
	OBJECTS	{tControllerName, tSerNum, tTrapText}
	STATUS	current
	DESCRIPTION	"Protection 1. level - res - alarm activated"
::= { notifications 33558256 }

tresL1Disappeared3	NOTIFICATION-TYPE
	OBJECTS	{tControllerName, tSerNum, tTrapText}
	STATUS	current
	DESCRIPTION	"Protection 1. level - res - alarm disappeared"
::= { notifications 33558257 }

tresL1AlarmReset3	NOTIFICATION-TYPE
	OBJECTS	{tControllerName, tSerNum, tTrapText}
	STATUS	current
	DESCRIPTION	"Protection 1. level - res - alarm reset"
::= { notifications 33558258 }

tresL2Activated3	NOTIFICATION-TYPE
	OBJECTS	{tControllerName, tSerNum, tTrapText}
	STATUS	current
	DESCRIPTION	"Protection 2. level - res - alarm activated"
::= { notifications 167775984 }

tresL2Disappeared3	NOTIFICATION-TYPE
	OBJECTS	{tControllerName, tSerNum, tTrapText}
	STATUS	current
	DESCRIPTION	"Protection 2. level - res - alarm disappeared"
::= { notifications 167775985 }

tresL2AlarmReset3	NOTIFICATION-TYPE
	OBJECTS	{tControllerName, tSerNum, tTrapText}
	STATUS	current
	DESCRIPTION	"Protection 2. level - res - alarm reset"
::= { notifications 167775986 }

tresSFActivated3	NOTIFICATION-TYPE
	OBJECTS	{tControllerName, tSerNum, tTrapText}
	STATUS	current
	DESCRIPTION	"Protection Sensor Fail - res - alarm activated"
::= { notifications 301993712 }

tresSFDisappeared3	NOTIFICATION-TYPE
	OBJECTS	{tControllerName, tSerNum, tTrapText}
	STATUS	current
	DESCRIPTION	"Protection Sensor Fail - res - alarm disappeared"
::= { notifications 301993713 }

tresSFAlarmReset3	NOTIFICATION-TYPE
	OBJECTS	{tControllerName, tSerNum, tTrapText}
	STATUS	current
	DESCRIPTION	"Protection Sensor Fail - res - alarm reset"
::= { notifications 301993714 }

tresL1Activated4	NOTIFICATION-TYPE
	OBJECTS	{tControllerName, tSerNum, tTrapText}
	STATUS	current
	DESCRIPTION	"Protection 1. level - res - alarm activated"
::= { notifications 33558260 }

tresL1Disappeared4	NOTIFICATION-TYPE
	OBJECTS	{tControllerName, tSerNum, tTrapText}
	STATUS	current
	DESCRIPTION	"Protection 1. level - res - alarm disappeared"
::= { notifications 33558261 }

tresL1AlarmReset4	NOTIFICATION-TYPE
	OBJECTS	{tControllerName, tSerNum, tTrapText}
	STATUS	current
	DESCRIPTION	"Protection 1. level - res - alarm reset"
::= { notifications 33558262 }

tresL2Activated4	NOTIFICATION-TYPE
	OBJECTS	{tControllerName, tSerNum, tTrapText}
	STATUS	current
	DESCRIPTION	"Protection 2. level - res - alarm activated"
::= { notifications 167775988 }

tresL2Disappeared4	NOTIFICATION-TYPE
	OBJECTS	{tControllerName, tSerNum, tTrapText}
	STATUS	current
	DESCRIPTION	"Protection 2. level - res - alarm disappeared"
::= { notifications 167775989 }

tresL2AlarmReset4	NOTIFICATION-TYPE
	OBJECTS	{tControllerName, tSerNum, tTrapText}
	STATUS	current
	DESCRIPTION	"Protection 2. level - res - alarm reset"
::= { notifications 167775990 }

tresSFActivated4	NOTIFICATION-TYPE
	OBJECTS	{tControllerName, tSerNum, tTrapText}
	STATUS	current
	DESCRIPTION	"Protection Sensor Fail - res - alarm activated"
::= { notifications 301993716 }

tresSFDisappeared4	NOTIFICATION-TYPE
	OBJECTS	{tControllerName, tSerNum, tTrapText}
	STATUS	current
	DESCRIPTION	"Protection Sensor Fail - res - alarm disappeared"
::= { notifications 301993717 }

tresSFAlarmReset4	NOTIFICATION-TYPE
	OBJECTS	{tControllerName, tSerNum, tTrapText}
	STATUS	current
	DESCRIPTION	"Protection Sensor Fail - res - alarm reset"
::= { notifications 301993718 }

tresL1Activated5	NOTIFICATION-TYPE
	OBJECTS	{tControllerName, tSerNum, tTrapText}
	STATUS	current
	DESCRIPTION	"Protection 1. level - res - alarm activated"
::= { notifications 33558264 }

tresL1Disappeared5	NOTIFICATION-TYPE
	OBJECTS	{tControllerName, tSerNum, tTrapText}
	STATUS	current
	DESCRIPTION	"Protection 1. level - res - alarm disappeared"
::= { notifications 33558265 }

tresL1AlarmReset5	NOTIFICATION-TYPE
	OBJECTS	{tControllerName, tSerNum, tTrapText}
	STATUS	current
	DESCRIPTION	"Protection 1. level - res - alarm reset"
::= { notifications 33558266 }

tresL2Activated5	NOTIFICATION-TYPE
	OBJECTS	{tControllerName, tSerNum, tTrapText}
	STATUS	current
	DESCRIPTION	"Protection 2. level - res - alarm activated"
::= { notifications 167775992 }

tresL2Disappeared5	NOTIFICATION-TYPE
	OBJECTS	{tControllerName, tSerNum, tTrapText}
	STATUS	current
	DESCRIPTION	"Protection 2. level - res - alarm disappeared"
::= { notifications 167775993 }

tresL2AlarmReset5	NOTIFICATION-TYPE
	OBJECTS	{tControllerName, tSerNum, tTrapText}
	STATUS	current
	DESCRIPTION	"Protection 2. level - res - alarm reset"
::= { notifications 167775994 }

tresSFActivated5	NOTIFICATION-TYPE
	OBJECTS	{tControllerName, tSerNum, tTrapText}
	STATUS	current
	DESCRIPTION	"Protection Sensor Fail - res - alarm activated"
::= { notifications 301993720 }

tresSFDisappeared5	NOTIFICATION-TYPE
	OBJECTS	{tControllerName, tSerNum, tTrapText}
	STATUS	current
	DESCRIPTION	"Protection Sensor Fail - res - alarm disappeared"
::= { notifications 301993721 }

tresSFAlarmReset5	NOTIFICATION-TYPE
	OBJECTS	{tControllerName, tSerNum, tTrapText}
	STATUS	current
	DESCRIPTION	"Protection Sensor Fail - res - alarm reset"
::= { notifications 301993722 }

tresL1Activated6	NOTIFICATION-TYPE
	OBJECTS	{tControllerName, tSerNum, tTrapText}
	STATUS	current
	DESCRIPTION	"Protection 1. level - res - alarm activated"
::= { notifications 33558268 }

tresL1Disappeared6	NOTIFICATION-TYPE
	OBJECTS	{tControllerName, tSerNum, tTrapText}
	STATUS	current
	DESCRIPTION	"Protection 1. level - res - alarm disappeared"
::= { notifications 33558269 }

tresL1AlarmReset6	NOTIFICATION-TYPE
	OBJECTS	{tControllerName, tSerNum, tTrapText}
	STATUS	current
	DESCRIPTION	"Protection 1. level - res - alarm reset"
::= { notifications 33558270 }

tresL2Activated6	NOTIFICATION-TYPE
	OBJECTS	{tControllerName, tSerNum, tTrapText}
	STATUS	current
	DESCRIPTION	"Protection 2. level - res - alarm activated"
::= { notifications 167775996 }

tresL2Disappeared6	NOTIFICATION-TYPE
	OBJECTS	{tControllerName, tSerNum, tTrapText}
	STATUS	current
	DESCRIPTION	"Protection 2. level - res - alarm disappeared"
::= { notifications 167775997 }

tresL2AlarmReset6	NOTIFICATION-TYPE
	OBJECTS	{tControllerName, tSerNum, tTrapText}
	STATUS	current
	DESCRIPTION	"Protection 2. level - res - alarm reset"
::= { notifications 167775998 }

tresSFActivated6	NOTIFICATION-TYPE
	OBJECTS	{tControllerName, tSerNum, tTrapText}
	STATUS	current
	DESCRIPTION	"Protection Sensor Fail - res - alarm activated"
::= { notifications 301993724 }

tresSFDisappeared6	NOTIFICATION-TYPE
	OBJECTS	{tControllerName, tSerNum, tTrapText}
	STATUS	current
	DESCRIPTION	"Protection Sensor Fail - res - alarm disappeared"
::= { notifications 301993725 }

tresSFAlarmReset6	NOTIFICATION-TYPE
	OBJECTS	{tControllerName, tSerNum, tTrapText}
	STATUS	current
	DESCRIPTION	"Protection Sensor Fail - res - alarm reset"
::= { notifications 301993726 }

tresL1Activated7	NOTIFICATION-TYPE
	OBJECTS	{tControllerName, tSerNum, tTrapText}
	STATUS	current
	DESCRIPTION	"Protection 1. level - res - alarm activated"
::= { notifications 33558272 }

tresL1Disappeared7	NOTIFICATION-TYPE
	OBJECTS	{tControllerName, tSerNum, tTrapText}
	STATUS	current
	DESCRIPTION	"Protection 1. level - res - alarm disappeared"
::= { notifications 33558273 }

tresL1AlarmReset7	NOTIFICATION-TYPE
	OBJECTS	{tControllerName, tSerNum, tTrapText}
	STATUS	current
	DESCRIPTION	"Protection 1. level - res - alarm reset"
::= { notifications 33558274 }

tresL2Activated7	NOTIFICATION-TYPE
	OBJECTS	{tControllerName, tSerNum, tTrapText}
	STATUS	current
	DESCRIPTION	"Protection 2. level - res - alarm activated"
::= { notifications 167776000 }

tresL2Disappeared7	NOTIFICATION-TYPE
	OBJECTS	{tControllerName, tSerNum, tTrapText}
	STATUS	current
	DESCRIPTION	"Protection 2. level - res - alarm disappeared"
::= { notifications 167776001 }

tresL2AlarmReset7	NOTIFICATION-TYPE
	OBJECTS	{tControllerName, tSerNum, tTrapText}
	STATUS	current
	DESCRIPTION	"Protection 2. level - res - alarm reset"
::= { notifications 167776002 }

tresSFActivated7	NOTIFICATION-TYPE
	OBJECTS	{tControllerName, tSerNum, tTrapText}
	STATUS	current
	DESCRIPTION	"Protection Sensor Fail - res - alarm activated"
::= { notifications 301993728 }

tresSFDisappeared7	NOTIFICATION-TYPE
	OBJECTS	{tControllerName, tSerNum, tTrapText}
	STATUS	current
	DESCRIPTION	"Protection Sensor Fail - res - alarm disappeared"
::= { notifications 301993729 }

tresSFAlarmReset7	NOTIFICATION-TYPE
	OBJECTS	{tControllerName, tSerNum, tTrapText}
	STATUS	current
	DESCRIPTION	"Protection Sensor Fail - res - alarm reset"
::= { notifications 301993730 }

tECUYellowLampL1Activated	NOTIFICATION-TYPE
	OBJECTS	{tControllerName, tSerNum, tTrapText}
	STATUS	current
	DESCRIPTION	"Protection 1. level - ECU Yellow Lamp - alarm activated"
::= { notifications 33557628 }

tECUYellowLampL1Disappeared	NOTIFICATION-TYPE
	OBJECTS	{tControllerName, tSerNum, tTrapText}
	STATUS	current
	DESCRIPTION	"Protection 1. level - ECU Yellow Lamp - alarm disappeared"
::= { notifications 33557629 }

tECUYellowLampL1AlarmReset	NOTIFICATION-TYPE
	OBJECTS	{tControllerName, tSerNum, tTrapText}
	STATUS	current
	DESCRIPTION	"Protection 1. level - ECU Yellow Lamp - alarm reset"
::= { notifications 33557630 }

tECURedLampL1Activated	NOTIFICATION-TYPE
	OBJECTS	{tControllerName, tSerNum, tTrapText}
	STATUS	current
	DESCRIPTION	"Protection 1. level - ECU Red Lamp - alarm activated"
::= { notifications 33558528 }

tECURedLampL1Disappeared	NOTIFICATION-TYPE
	OBJECTS	{tControllerName, tSerNum, tTrapText}
	STATUS	current
	DESCRIPTION	"Protection 1. level - ECU Red Lamp - alarm disappeared"
::= { notifications 33558529 }

tECURedLampL1AlarmReset	NOTIFICATION-TYPE
	OBJECTS	{tControllerName, tSerNum, tTrapText}
	STATUS	current
	DESCRIPTION	"Protection 1. level - ECU Red Lamp - alarm reset"
::= { notifications 33558530 }

tECUWaitToStartL1Activated	NOTIFICATION-TYPE
	OBJECTS	{tControllerName, tSerNum, tTrapText}
	STATUS	current
	DESCRIPTION	"Protection 1. level - ECU Wait To Start - alarm activated"
::= { notifications 33557644 }

tECUWaitToStartL1Disappeared	NOTIFICATION-TYPE
	OBJECTS	{tControllerName, tSerNum, tTrapText}
	STATUS	current
	DESCRIPTION	"Protection 1. level - ECU Wait To Start - alarm disappeared"
::= { notifications 33557645 }

tECUWaitToStartL1AlarmReset	NOTIFICATION-TYPE
	OBJECTS	{tControllerName, tSerNum, tTrapText}
	STATUS	current
	DESCRIPTION	"Protection 1. level - ECU Wait To Start - alarm reset"
::= { notifications 33557646 }

tATTDPFLampL1Activated	NOTIFICATION-TYPE
	OBJECTS	{tControllerName, tSerNum, tTrapText}
	STATUS	current
	DESCRIPTION	"Protection 1. level - ATT DPF Lamp - alarm activated"
::= { notifications 33558700 }

tATTDPFLampL1Disappeared	NOTIFICATION-TYPE
	OBJECTS	{tControllerName, tSerNum, tTrapText}
	STATUS	current
	DESCRIPTION	"Protection 1. level - ATT DPF Lamp - alarm disappeared"
::= { notifications 33558701 }

tATTDPFLampL1AlarmReset	NOTIFICATION-TYPE
	OBJECTS	{tControllerName, tSerNum, tTrapText}
	STATUS	current
	DESCRIPTION	"Protection 1. level - ATT DPF Lamp - alarm reset"
::= { notifications 33558702 }

tATTHESTLampL1Activated	NOTIFICATION-TYPE
	OBJECTS	{tControllerName, tSerNum, tTrapText}
	STATUS	current
	DESCRIPTION	"Protection 1. level - ATT HEST Lamp - alarm activated"
::= { notifications 33558540 }

tATTHESTLampL1Disappeared	NOTIFICATION-TYPE
	OBJECTS	{tControllerName, tSerNum, tTrapText}
	STATUS	current
	DESCRIPTION	"Protection 1. level - ATT HEST Lamp - alarm disappeared"
::= { notifications 33558541 }

tATTHESTLampL1AlarmReset	NOTIFICATION-TYPE
	OBJECTS	{tControllerName, tSerNum, tTrapText}
	STATUS	current
	DESCRIPTION	"Protection 1. level - ATT HEST Lamp - alarm reset"
::= { notifications 33558542 }

tATTSCRErrorLampL1Activated	NOTIFICATION-TYPE
	OBJECTS	{tControllerName, tSerNum, tTrapText}
	STATUS	current
	DESCRIPTION	"Protection 1. level - ATT SCR Error Lamp - alarm activated"
::= { notifications 33558544 }

tATTSCRErrorLampL1Disappeared	NOTIFICATION-TYPE
	OBJECTS	{tControllerName, tSerNum, tTrapText}
	STATUS	current
	DESCRIPTION	"Protection 1. level - ATT SCR Error Lamp - alarm disappeared"
::= { notifications 33558545 }

tATTSCRErrorLampL1AlarmReset	NOTIFICATION-TYPE
	OBJECTS	{tControllerName, tSerNum, tTrapText}
	STATUS	current
	DESCRIPTION	"Protection 1. level - ATT SCR Error Lamp - alarm reset"
::= { notifications 33558546 }

tATTDEFLevelLampL1Activated	NOTIFICATION-TYPE
	OBJECTS	{tControllerName, tSerNum, tTrapText}
	STATUS	current
	DESCRIPTION	"Protection 1. level - ATT DEF Level Lamp - alarm activated"
::= { notifications 33558548 }

tATTDEFLevelLampL1Disappeared	NOTIFICATION-TYPE
	OBJECTS	{tControllerName, tSerNum, tTrapText}
	STATUS	current
	DESCRIPTION	"Protection 1. level - ATT DEF Level Lamp - alarm disappeared"
::= { notifications 33558549 }

tATTDEFLevelLampL1AlarmReset	NOTIFICATION-TYPE
	OBJECTS	{tControllerName, tSerNum, tTrapText}
	STATUS	current
	DESCRIPTION	"Protection 1. level - ATT DEF Level Lamp - alarm reset"
::= { notifications 33558550 }

tATTInhibitedLampL1Activated	NOTIFICATION-TYPE
	OBJECTS	{tControllerName, tSerNum, tTrapText}
	STATUS	current
	DESCRIPTION	"Protection 1. level - ATT Inhibited Lamp - alarm activated"
::= { notifications 33557672 }

tATTInhibitedLampL1Disappeared	NOTIFICATION-TYPE
	OBJECTS	{tControllerName, tSerNum, tTrapText}
	STATUS	current
	DESCRIPTION	"Protection 1. level - ATT Inhibited Lamp - alarm disappeared"
::= { notifications 33557673 }

tATTInhibitedLampL1AlarmReset	NOTIFICATION-TYPE
	OBJECTS	{tControllerName, tSerNum, tTrapText}
	STATUS	current
	DESCRIPTION	"Protection 1. level - ATT Inhibited Lamp - alarm reset"
::= { notifications 33557674 }

tATTInterlockActiveL1Activated	NOTIFICATION-TYPE
	OBJECTS	{tControllerName, tSerNum, tTrapText}
	STATUS	current
	DESCRIPTION	"Protection 1. level - ATT Interlock Active - alarm activated"
::= { notifications 33558852 }

tATTInterlockActiveL1Disappeared	NOTIFICATION-TYPE
	OBJECTS	{tControllerName, tSerNum, tTrapText}
	STATUS	current
	DESCRIPTION	"Protection 1. level - ATT Interlock Active - alarm disappeared"
::= { notifications 33558853 }

tATTInterlockActiveL1AlarmReset	NOTIFICATION-TYPE
	OBJECTS	{tControllerName, tSerNum, tTrapText}
	STATUS	current
	DESCRIPTION	"Protection 1. level - ATT Interlock Active - alarm reset"
::= { notifications 33558854 }

tATTForceRegenActiveL1Activated	NOTIFICATION-TYPE
	OBJECTS	{tControllerName, tSerNum, tTrapText}
	STATUS	current
	DESCRIPTION	"Protection 1. level - ATT Force Regen Active - alarm activated"
::= { notifications 33559456 }

tATTForceRegenActiveL1Disappeared	NOTIFICATION-TYPE
	OBJECTS	{tControllerName, tSerNum, tTrapText}
	STATUS	current
	DESCRIPTION	"Protection 1. level - ATT Force Regen Active - alarm disappeared"
::= { notifications 33559457 }

tATTForceRegenActiveL1AlarmReset	NOTIFICATION-TYPE
	OBJECTS	{tControllerName, tSerNum, tTrapText}
	STATUS	current
	DESCRIPTION	"Protection 1. level - ATT Force Regen Active - alarm reset"
::= { notifications 33559458 }

tDPFRegenWithProtectionsOffL1Activated	NOTIFICATION-TYPE
	OBJECTS	{tControllerName, tSerNum, tTrapText}
	STATUS	current
	DESCRIPTION	"Protection 1. level - DPF Regen with protections off - alarm activated"
::= { notifications 33563936 }

tDPFRegenWithProtectionsOffL1Disappeared	NOTIFICATION-TYPE
	OBJECTS	{tControllerName, tSerNum, tTrapText}
	STATUS	current
	DESCRIPTION	"Protection 1. level - DPF Regen with protections off - alarm disappeared"
::= { notifications 33563937 }

tDPFRegenWithProtectionsOffL1AlarmReset	NOTIFICATION-TYPE
	OBJECTS	{tControllerName, tSerNum, tTrapText}
	STATUS	current
	DESCRIPTION	"Protection 1. level - DPF Regen with protections off - alarm reset"
::= { notifications 33563938 }

tATTInhibRegenActiveL1Activated	NOTIFICATION-TYPE
	OBJECTS	{tControllerName, tSerNum, tTrapText}
	STATUS	current
	DESCRIPTION	"Protection 1. level - ATT Inhib Regen Active - alarm activated"
::= { notifications 33559460 }

tATTInhibRegenActiveL1Disappeared	NOTIFICATION-TYPE
	OBJECTS	{tControllerName, tSerNum, tTrapText}
	STATUS	current
	DESCRIPTION	"Protection 1. level - ATT Inhib Regen Active - alarm disappeared"
::= { notifications 33559461 }

tATTInhibRegenActiveL1AlarmReset	NOTIFICATION-TYPE
	OBJECTS	{tControllerName, tSerNum, tTrapText}
	STATUS	current
	DESCRIPTION	"Protection 1. level - ATT Inhib Regen Active - alarm reset"
::= { notifications 33559462 }

tLSD500ParamWriteFailL1Activated	NOTIFICATION-TYPE
	OBJECTS	{tControllerName, tSerNum, tTrapText}
	STATUS	current
	DESCRIPTION	"Protection 1. level - LS D500 Param Write Fail - alarm activated"
::= { notifications 33561000 }

tLSD500ParamWriteFailL1Disappeared	NOTIFICATION-TYPE
	OBJECTS	{tControllerName, tSerNum, tTrapText}
	STATUS	current
	DESCRIPTION	"Protection 1. level - LS D500 Param Write Fail - alarm disappeared"
::= { notifications 33561001 }

tLSD500ParamWriteFailL1AlarmReset	NOTIFICATION-TYPE
	OBJECTS	{tControllerName, tSerNum, tTrapText}
	STATUS	current
	DESCRIPTION	"Protection 1. level - LS D500 Param Write Fail - alarm reset"
::= { notifications 33561002 }

tDisplayFailL1Activated	NOTIFICATION-TYPE
	OBJECTS	{tControllerName, tSerNum, tTrapText}
	STATUS	current
	DESCRIPTION	"Protection 1. level - Display Fail - alarm activated"
::= { notifications 33558732 }

tDisplayFailL1Disappeared	NOTIFICATION-TYPE
	OBJECTS	{tControllerName, tSerNum, tTrapText}
	STATUS	current
	DESCRIPTION	"Protection 1. level - Display Fail - alarm disappeared"
::= { notifications 33558733 }

tDisplayFailL1AlarmReset	NOTIFICATION-TYPE
	OBJECTS	{tControllerName, tSerNum, tTrapText}
	STATUS	current
	DESCRIPTION	"Protection 1. level - Display Fail - alarm reset"
::= { notifications 33558734 }

tDefaultPasswordL1Activated	NOTIFICATION-TYPE
	OBJECTS	{tControllerName, tSerNum, tTrapText}
	STATUS	current
	DESCRIPTION	"Protection 1. level - Default Password - alarm activated"
::= { notifications 33558716 }

tDefaultPasswordL1Disappeared	NOTIFICATION-TYPE
	OBJECTS	{tControllerName, tSerNum, tTrapText}
	STATUS	current
	DESCRIPTION	"Protection 1. level - Default Password - alarm disappeared"
::= { notifications 33558717 }

tDefaultPasswordL1AlarmReset	NOTIFICATION-TYPE
	OBJECTS	{tControllerName, tSerNum, tTrapText}
	STATUS	current
	DESCRIPTION	"Protection 1. level - Default Password - alarm reset"
::= { notifications 33558718 }

tBruteForceProtectionActiveL1Activated	NOTIFICATION-TYPE
	OBJECTS	{tControllerName, tSerNum, tTrapText}
	STATUS	current
	DESCRIPTION	"Protection 1. level - Brute Force Protection Active - alarm activated"
::= { notifications 33559380 }

tBruteForceProtectionActiveL1Disappeared	NOTIFICATION-TYPE
	OBJECTS	{tControllerName, tSerNum, tTrapText}
	STATUS	current
	DESCRIPTION	"Protection 1. level - Brute Force Protection Active - alarm disappeared"
::= { notifications 33559381 }

tBruteForceProtectionActiveL1AlarmReset	NOTIFICATION-TYPE
	OBJECTS	{tControllerName, tSerNum, tTrapText}
	STATUS	current
	DESCRIPTION	"Protection 1. level - Brute Force Protection Active - alarm reset"
::= { notifications 33559382 }

tProductionModeL1Activated	NOTIFICATION-TYPE
	OBJECTS	{tControllerName, tSerNum, tTrapText}
	STATUS	current
	DESCRIPTION	"Protection 1. level - Production Mode - alarm activated"
::= { notifications 33559548 }

tProductionModeL1Disappeared	NOTIFICATION-TYPE
	OBJECTS	{tControllerName, tSerNum, tTrapText}
	STATUS	current
	DESCRIPTION	"Protection 1. level - Production Mode - alarm disappeared"
::= { notifications 33559549 }

tProductionModeL1AlarmReset	NOTIFICATION-TYPE
	OBJECTS	{tControllerName, tSerNum, tTrapText}
	STATUS	current
	DESCRIPTION	"Protection 1. level - Production Mode - alarm reset"
::= { notifications 33559550 }

tPasswordResetEMailAddrIsNotSetL1Activated	NOTIFICATION-TYPE
	OBJECTS	{tControllerName, tSerNum, tTrapText}
	STATUS	current
	DESCRIPTION	"Protection 1. level - Password reset e-mail addr is not set - alarm activated"
::= { notifications 33559600 }

tPasswordResetEMailAddrIsNotSetL1Disappeared	NOTIFICATION-TYPE
	OBJECTS	{tControllerName, tSerNum, tTrapText}
	STATUS	current
	DESCRIPTION	"Protection 1. level - Password reset e-mail addr is not set - alarm disappeared"
::= { notifications 33559601 }

tPasswordResetEMailAddrIsNotSetL1AlarmReset	NOTIFICATION-TYPE
	OBJECTS	{tControllerName, tSerNum, tTrapText}
	STATUS	current
	DESCRIPTION	"Protection 1. level - Password reset e-mail addr is not set - alarm reset"
::= { notifications 33559602 }

tSHBINCollisionL1Activated	NOTIFICATION-TYPE
	OBJECTS	{tControllerName, tSerNum, tTrapText}
	STATUS	current
	DESCRIPTION	"Protection 1. level - SHBIN Collision - alarm activated"
::= { notifications 33554580 }

tSHBINCollisionL1Disappeared	NOTIFICATION-TYPE
	OBJECTS	{tControllerName, tSerNum, tTrapText}
	STATUS	current
	DESCRIPTION	"Protection 1. level - SHBIN Collision - alarm disappeared"
::= { notifications 33554581 }

tSHBINCollisionL1AlarmReset	NOTIFICATION-TYPE
	OBJECTS	{tControllerName, tSerNum, tTrapText}
	STATUS	current
	DESCRIPTION	"Protection 1. level - SHBIN Collision - alarm reset"
::= { notifications 33554582 }

tSHAINCollisionL1Activated	NOTIFICATION-TYPE
	OBJECTS	{tControllerName, tSerNum, tTrapText}
	STATUS	current
	DESCRIPTION	"Protection 1. level - SHAIN Collision - alarm activated"
::= { notifications 33554584 }

tSHAINCollisionL1Disappeared	NOTIFICATION-TYPE
	OBJECTS	{tControllerName, tSerNum, tTrapText}
	STATUS	current
	DESCRIPTION	"Protection 1. level - SHAIN Collision - alarm disappeared"
::= { notifications 33554585 }

tSHAINCollisionL1AlarmReset	NOTIFICATION-TYPE
	OBJECTS	{tControllerName, tSerNum, tTrapText}
	STATUS	current
	DESCRIPTION	"Protection 1. level - SHAIN Collision - alarm reset"
::= { notifications 33554586 }

tSHBIN1L1Activated	NOTIFICATION-TYPE
	OBJECTS	{tControllerName, tSerNum, tTrapText}
	STATUS	current
	DESCRIPTION	"Protection 1. level - SHBIN 1 - alarm activated"
::= { notifications 33554560 }

tSHBIN1L1Disappeared	NOTIFICATION-TYPE
	OBJECTS	{tControllerName, tSerNum, tTrapText}
	STATUS	current
	DESCRIPTION	"Protection 1. level - SHBIN 1 - alarm disappeared"
::= { notifications 33554561 }

tSHBIN1L1AlarmReset	NOTIFICATION-TYPE
	OBJECTS	{tControllerName, tSerNum, tTrapText}
	STATUS	current
	DESCRIPTION	"Protection 1. level - SHBIN 1 - alarm reset"
::= { notifications 33554562 }

tSHBIN1L2Activated	NOTIFICATION-TYPE
	OBJECTS	{tControllerName, tSerNum, tTrapText}
	STATUS	current
	DESCRIPTION	"Protection 2. level - SHBIN 1 - alarm activated"
::= { notifications 167772288 }

tSHBIN1L2Disappeared	NOTIFICATION-TYPE
	OBJECTS	{tControllerName, tSerNum, tTrapText}
	STATUS	current
	DESCRIPTION	"Protection 2. level - SHBIN 1 - alarm disappeared"
::= { notifications 167772289 }

tSHBIN1L2AlarmReset	NOTIFICATION-TYPE
	OBJECTS	{tControllerName, tSerNum, tTrapText}
	STATUS	current
	DESCRIPTION	"Protection 2. level - SHBIN 1 - alarm reset"
::= { notifications 167772290 }

tSHBIN2L1Activated	NOTIFICATION-TYPE
	OBJECTS	{tControllerName, tSerNum, tTrapText}
	STATUS	current
	DESCRIPTION	"Protection 1. level - SHBIN 2 - alarm activated"
::= { notifications 33554564 }

tSHBIN2L1Disappeared	NOTIFICATION-TYPE
	OBJECTS	{tControllerName, tSerNum, tTrapText}
	STATUS	current
	DESCRIPTION	"Protection 1. level - SHBIN 2 - alarm disappeared"
::= { notifications 33554565 }

tSHBIN2L1AlarmReset	NOTIFICATION-TYPE
	OBJECTS	{tControllerName, tSerNum, tTrapText}
	STATUS	current
	DESCRIPTION	"Protection 1. level - SHBIN 2 - alarm reset"
::= { notifications 33554566 }

tSHBIN2L2Activated	NOTIFICATION-TYPE
	OBJECTS	{tControllerName, tSerNum, tTrapText}
	STATUS	current
	DESCRIPTION	"Protection 2. level - SHBIN 2 - alarm activated"
::= { notifications 167772292 }

tSHBIN2L2Disappeared	NOTIFICATION-TYPE
	OBJECTS	{tControllerName, tSerNum, tTrapText}
	STATUS	current
	DESCRIPTION	"Protection 2. level - SHBIN 2 - alarm disappeared"
::= { notifications 167772293 }

tSHBIN2L2AlarmReset	NOTIFICATION-TYPE
	OBJECTS	{tControllerName, tSerNum, tTrapText}
	STATUS	current
	DESCRIPTION	"Protection 2. level - SHBIN 2 - alarm reset"
::= { notifications 167772294 }

tSHBIN3L1Activated	NOTIFICATION-TYPE
	OBJECTS	{tControllerName, tSerNum, tTrapText}
	STATUS	current
	DESCRIPTION	"Protection 1. level - SHBIN 3 - alarm activated"
::= { notifications 33554568 }

tSHBIN3L1Disappeared	NOTIFICATION-TYPE
	OBJECTS	{tControllerName, tSerNum, tTrapText}
	STATUS	current
	DESCRIPTION	"Protection 1. level - SHBIN 3 - alarm disappeared"
::= { notifications 33554569 }

tSHBIN3L1AlarmReset	NOTIFICATION-TYPE
	OBJECTS	{tControllerName, tSerNum, tTrapText}
	STATUS	current
	DESCRIPTION	"Protection 1. level - SHBIN 3 - alarm reset"
::= { notifications 33554570 }

tSHBIN3L2Activated	NOTIFICATION-TYPE
	OBJECTS	{tControllerName, tSerNum, tTrapText}
	STATUS	current
	DESCRIPTION	"Protection 2. level - SHBIN 3 - alarm activated"
::= { notifications 167772296 }

tSHBIN3L2Disappeared	NOTIFICATION-TYPE
	OBJECTS	{tControllerName, tSerNum, tTrapText}
	STATUS	current
	DESCRIPTION	"Protection 2. level - SHBIN 3 - alarm disappeared"
::= { notifications 167772297 }

tSHBIN3L2AlarmReset	NOTIFICATION-TYPE
	OBJECTS	{tControllerName, tSerNum, tTrapText}
	STATUS	current
	DESCRIPTION	"Protection 2. level - SHBIN 3 - alarm reset"
::= { notifications 167772298 }

tSHBIN4L1Activated	NOTIFICATION-TYPE
	OBJECTS	{tControllerName, tSerNum, tTrapText}
	STATUS	current
	DESCRIPTION	"Protection 1. level - SHBIN 4 - alarm activated"
::= { notifications 33554572 }

tSHBIN4L1Disappeared	NOTIFICATION-TYPE
	OBJECTS	{tControllerName, tSerNum, tTrapText}
	STATUS	current
	DESCRIPTION	"Protection 1. level - SHBIN 4 - alarm disappeared"
::= { notifications 33554573 }

tSHBIN4L1AlarmReset	NOTIFICATION-TYPE
	OBJECTS	{tControllerName, tSerNum, tTrapText}
	STATUS	current
	DESCRIPTION	"Protection 1. level - SHBIN 4 - alarm reset"
::= { notifications 33554574 }

tSHBIN4L2Activated	NOTIFICATION-TYPE
	OBJECTS	{tControllerName, tSerNum, tTrapText}
	STATUS	current
	DESCRIPTION	"Protection 2. level - SHBIN 4 - alarm activated"
::= { notifications 167772300 }

tSHBIN4L2Disappeared	NOTIFICATION-TYPE
	OBJECTS	{tControllerName, tSerNum, tTrapText}
	STATUS	current
	DESCRIPTION	"Protection 2. level - SHBIN 4 - alarm disappeared"
::= { notifications 167772301 }

tSHBIN4L2AlarmReset	NOTIFICATION-TYPE
	OBJECTS	{tControllerName, tSerNum, tTrapText}
	STATUS	current
	DESCRIPTION	"Protection 2. level - SHBIN 4 - alarm reset"
::= { notifications 167772302 }

tSHBIN5L1Activated	NOTIFICATION-TYPE
	OBJECTS	{tControllerName, tSerNum, tTrapText}
	STATUS	current
	DESCRIPTION	"Protection 1. level - SHBIN 5 - alarm activated"
::= { notifications 33555296 }

tSHBIN5L1Disappeared	NOTIFICATION-TYPE
	OBJECTS	{tControllerName, tSerNum, tTrapText}
	STATUS	current
	DESCRIPTION	"Protection 1. level - SHBIN 5 - alarm disappeared"
::= { notifications 33555297 }

tSHBIN5L1AlarmReset	NOTIFICATION-TYPE
	OBJECTS	{tControllerName, tSerNum, tTrapText}
	STATUS	current
	DESCRIPTION	"Protection 1. level - SHBIN 5 - alarm reset"
::= { notifications 33555298 }

tSHBIN5L2Activated	NOTIFICATION-TYPE
	OBJECTS	{tControllerName, tSerNum, tTrapText}
	STATUS	current
	DESCRIPTION	"Protection 2. level - SHBIN 5 - alarm activated"
::= { notifications 167773024 }

tSHBIN5L2Disappeared	NOTIFICATION-TYPE
	OBJECTS	{tControllerName, tSerNum, tTrapText}
	STATUS	current
	DESCRIPTION	"Protection 2. level - SHBIN 5 - alarm disappeared"
::= { notifications 167773025 }

tSHBIN5L2AlarmReset	NOTIFICATION-TYPE
	OBJECTS	{tControllerName, tSerNum, tTrapText}
	STATUS	current
	DESCRIPTION	"Protection 2. level - SHBIN 5 - alarm reset"
::= { notifications 167773026 }

tSHBIN6L1Activated	NOTIFICATION-TYPE
	OBJECTS	{tControllerName, tSerNum, tTrapText}
	STATUS	current
	DESCRIPTION	"Protection 1. level - SHBIN 6 - alarm activated"
::= { notifications 33555300 }

tSHBIN6L1Disappeared	NOTIFICATION-TYPE
	OBJECTS	{tControllerName, tSerNum, tTrapText}
	STATUS	current
	DESCRIPTION	"Protection 1. level - SHBIN 6 - alarm disappeared"
::= { notifications 33555301 }

tSHBIN6L1AlarmReset	NOTIFICATION-TYPE
	OBJECTS	{tControllerName, tSerNum, tTrapText}
	STATUS	current
	DESCRIPTION	"Protection 1. level - SHBIN 6 - alarm reset"
::= { notifications 33555302 }

tSHBIN6L2Activated	NOTIFICATION-TYPE
	OBJECTS	{tControllerName, tSerNum, tTrapText}
	STATUS	current
	DESCRIPTION	"Protection 2. level - SHBIN 6 - alarm activated"
::= { notifications 167773028 }

tSHBIN6L2Disappeared	NOTIFICATION-TYPE
	OBJECTS	{tControllerName, tSerNum, tTrapText}
	STATUS	current
	DESCRIPTION	"Protection 2. level - SHBIN 6 - alarm disappeared"
::= { notifications 167773029 }

tSHBIN6L2AlarmReset	NOTIFICATION-TYPE
	OBJECTS	{tControllerName, tSerNum, tTrapText}
	STATUS	current
	DESCRIPTION	"Protection 2. level - SHBIN 6 - alarm reset"
::= { notifications 167773030 }

tSHAIN1L1Activated	NOTIFICATION-TYPE
	OBJECTS	{tControllerName, tSerNum, tTrapText}
	STATUS	current
	DESCRIPTION	"Protection 1. level - SHAIN 1 - alarm activated"
::= { notifications 33554576 }

tSHAIN1L1Disappeared	NOTIFICATION-TYPE
	OBJECTS	{tControllerName, tSerNum, tTrapText}
	STATUS	current
	DESCRIPTION	"Protection 1. level - SHAIN 1 - alarm disappeared"
::= { notifications 33554577 }

tSHAIN1L1AlarmReset	NOTIFICATION-TYPE
	OBJECTS	{tControllerName, tSerNum, tTrapText}
	STATUS	current
	DESCRIPTION	"Protection 1. level - SHAIN 1 - alarm reset"
::= { notifications 33554578 }

tSHAIN1L2Activated	NOTIFICATION-TYPE
	OBJECTS	{tControllerName, tSerNum, tTrapText}
	STATUS	current
	DESCRIPTION	"Protection 2. level - SHAIN 1 - alarm activated"
::= { notifications 167772304 }

tSHAIN1L2Disappeared	NOTIFICATION-TYPE
	OBJECTS	{tControllerName, tSerNum, tTrapText}
	STATUS	current
	DESCRIPTION	"Protection 2. level - SHAIN 1 - alarm disappeared"
::= { notifications 167772305 }

tSHAIN1L2AlarmReset	NOTIFICATION-TYPE
	OBJECTS	{tControllerName, tSerNum, tTrapText}
	STATUS	current
	DESCRIPTION	"Protection 2. level - SHAIN 1 - alarm reset"
::= { notifications 167772306 }

tSHAIN2L1Activated	NOTIFICATION-TYPE
	OBJECTS	{tControllerName, tSerNum, tTrapText}
	STATUS	current
	DESCRIPTION	"Protection 1. level - SHAIN 2 - alarm activated"
::= { notifications 33555364 }

tSHAIN2L1Disappeared	NOTIFICATION-TYPE
	OBJECTS	{tControllerName, tSerNum, tTrapText}
	STATUS	current
	DESCRIPTION	"Protection 1. level - SHAIN 2 - alarm disappeared"
::= { notifications 33555365 }

tSHAIN2L1AlarmReset	NOTIFICATION-TYPE
	OBJECTS	{tControllerName, tSerNum, tTrapText}
	STATUS	current
	DESCRIPTION	"Protection 1. level - SHAIN 2 - alarm reset"
::= { notifications 33555366 }

tSHAIN2L2Activated	NOTIFICATION-TYPE
	OBJECTS	{tControllerName, tSerNum, tTrapText}
	STATUS	current
	DESCRIPTION	"Protection 2. level - SHAIN 2 - alarm activated"
::= { notifications 167773092 }

tSHAIN2L2Disappeared	NOTIFICATION-TYPE
	OBJECTS	{tControllerName, tSerNum, tTrapText}
	STATUS	current
	DESCRIPTION	"Protection 2. level - SHAIN 2 - alarm disappeared"
::= { notifications 167773093 }

tSHAIN2L2AlarmReset	NOTIFICATION-TYPE
	OBJECTS	{tControllerName, tSerNum, tTrapText}
	STATUS	current
	DESCRIPTION	"Protection 2. level - SHAIN 2 - alarm reset"
::= { notifications 167773094 }

tresL1Activated8	NOTIFICATION-TYPE
	OBJECTS	{tControllerName, tSerNum, tTrapText}
	STATUS	current
	DESCRIPTION	"Protection 1. level - res - alarm activated"
::= { notifications 33555908 }

tresL1Disappeared8	NOTIFICATION-TYPE
	OBJECTS	{tControllerName, tSerNum, tTrapText}
	STATUS	current
	DESCRIPTION	"Protection 1. level - res - alarm disappeared"
::= { notifications 33555909 }

tresL1AlarmReset8	NOTIFICATION-TYPE
	OBJECTS	{tControllerName, tSerNum, tTrapText}
	STATUS	current
	DESCRIPTION	"Protection 1. level - res - alarm reset"
::= { notifications 33555910 }

tresL2Activated8	NOTIFICATION-TYPE
	OBJECTS	{tControllerName, tSerNum, tTrapText}
	STATUS	current
	DESCRIPTION	"Protection 2. level - res - alarm activated"
::= { notifications 167773636 }

tresL2Disappeared8	NOTIFICATION-TYPE
	OBJECTS	{tControllerName, tSerNum, tTrapText}
	STATUS	current
	DESCRIPTION	"Protection 2. level - res - alarm disappeared"
::= { notifications 167773637 }

tresL2AlarmReset8	NOTIFICATION-TYPE
	OBJECTS	{tControllerName, tSerNum, tTrapText}
	STATUS	current
	DESCRIPTION	"Protection 2. level - res - alarm reset"
::= { notifications 167773638 }

tresSFActivated8	NOTIFICATION-TYPE
	OBJECTS	{tControllerName, tSerNum, tTrapText}
	STATUS	current
	DESCRIPTION	"Protection Sensor Fail - res - alarm activated"
::= { notifications 301991364 }

tresSFDisappeared8	NOTIFICATION-TYPE
	OBJECTS	{tControllerName, tSerNum, tTrapText}
	STATUS	current
	DESCRIPTION	"Protection Sensor Fail - res - alarm disappeared"
::= { notifications 301991365 }

tresSFAlarmReset8	NOTIFICATION-TYPE
	OBJECTS	{tControllerName, tSerNum, tTrapText}
	STATUS	current
	DESCRIPTION	"Protection Sensor Fail - res - alarm reset"
::= { notifications 301991366 }

tresL1Activated9	NOTIFICATION-TYPE
	OBJECTS	{tControllerName, tSerNum, tTrapText}
	STATUS	current
	DESCRIPTION	"Protection 1. level - res - alarm activated"
::= { notifications 33555912 }

tresL1Disappeared9	NOTIFICATION-TYPE
	OBJECTS	{tControllerName, tSerNum, tTrapText}
	STATUS	current
	DESCRIPTION	"Protection 1. level - res - alarm disappeared"
::= { notifications 33555913 }

tresL1AlarmReset9	NOTIFICATION-TYPE
	OBJECTS	{tControllerName, tSerNum, tTrapText}
	STATUS	current
	DESCRIPTION	"Protection 1. level - res - alarm reset"
::= { notifications 33555914 }

tresL2Activated9	NOTIFICATION-TYPE
	OBJECTS	{tControllerName, tSerNum, tTrapText}
	STATUS	current
	DESCRIPTION	"Protection 2. level - res - alarm activated"
::= { notifications 167773640 }

tresL2Disappeared9	NOTIFICATION-TYPE
	OBJECTS	{tControllerName, tSerNum, tTrapText}
	STATUS	current
	DESCRIPTION	"Protection 2. level - res - alarm disappeared"
::= { notifications 167773641 }

tresL2AlarmReset9	NOTIFICATION-TYPE
	OBJECTS	{tControllerName, tSerNum, tTrapText}
	STATUS	current
	DESCRIPTION	"Protection 2. level - res - alarm reset"
::= { notifications 167773642 }

tresSFActivated9	NOTIFICATION-TYPE
	OBJECTS	{tControllerName, tSerNum, tTrapText}
	STATUS	current
	DESCRIPTION	"Protection Sensor Fail - res - alarm activated"
::= { notifications 301991368 }

tresSFDisappeared9	NOTIFICATION-TYPE
	OBJECTS	{tControllerName, tSerNum, tTrapText}
	STATUS	current
	DESCRIPTION	"Protection Sensor Fail - res - alarm disappeared"
::= { notifications 301991369 }

tresSFAlarmReset9	NOTIFICATION-TYPE
	OBJECTS	{tControllerName, tSerNum, tTrapText}
	STATUS	current
	DESCRIPTION	"Protection Sensor Fail - res - alarm reset"
::= { notifications 301991370 }

tStopFailL1Activated	NOTIFICATION-TYPE
	OBJECTS	{tControllerName, tSerNum, tTrapText}
	STATUS	current
	DESCRIPTION	"Protection 1. level - Stop Fail - alarm activated"
::= { notifications 33554624 }

tStopFailL1Disappeared	NOTIFICATION-TYPE
	OBJECTS	{tControllerName, tSerNum, tTrapText}
	STATUS	current
	DESCRIPTION	"Protection 1. level - Stop Fail - alarm disappeared"
::= { notifications 33554625 }

tStopFailL1AlarmReset	NOTIFICATION-TYPE
	OBJECTS	{tControllerName, tSerNum, tTrapText}
	STATUS	current
	DESCRIPTION	"Protection 1. level - Stop Fail - alarm reset"
::= { notifications 33554626 }

tMaintenanceTimer1RunHoursL1Activated	NOTIFICATION-TYPE
	OBJECTS	{tControllerName, tSerNum, tTrapText}
	STATUS	current
	DESCRIPTION	"Protection 1. level - Maintenance Timer 1 RunHours - alarm activated"
::= { notifications 33556772 }

tMaintenanceTimer1RunHoursL1Disappeared	NOTIFICATION-TYPE
	OBJECTS	{tControllerName, tSerNum, tTrapText}
	STATUS	current
	DESCRIPTION	"Protection 1. level - Maintenance Timer 1 RunHours - alarm disappeared"
::= { notifications 33556773 }

tMaintenanceTimer1RunHoursL1AlarmReset	NOTIFICATION-TYPE
	OBJECTS	{tControllerName, tSerNum, tTrapText}
	STATUS	current
	DESCRIPTION	"Protection 1. level - Maintenance Timer 1 RunHours - alarm reset"
::= { notifications 33556774 }

tMaintenanceTimer1RunHoursL2Activated	NOTIFICATION-TYPE
	OBJECTS	{tControllerName, tSerNum, tTrapText}
	STATUS	current
	DESCRIPTION	"Protection 2. level - Maintenance Timer 1 RunHours - alarm activated"
::= { notifications 167774500 }

tMaintenanceTimer1RunHoursL2Disappeared	NOTIFICATION-TYPE
	OBJECTS	{tControllerName, tSerNum, tTrapText}
	STATUS	current
	DESCRIPTION	"Protection 2. level - Maintenance Timer 1 RunHours - alarm disappeared"
::= { notifications 167774501 }

tMaintenanceTimer1RunHoursL2AlarmReset	NOTIFICATION-TYPE
	OBJECTS	{tControllerName, tSerNum, tTrapText}
	STATUS	current
	DESCRIPTION	"Protection 2. level - Maintenance Timer 1 RunHours - alarm reset"
::= { notifications 167774502 }

tMaintenanceTimer2RunHoursL1Activated	NOTIFICATION-TYPE
	OBJECTS	{tControllerName, tSerNum, tTrapText}
	STATUS	current
	DESCRIPTION	"Protection 1. level - Maintenance Timer 2 RunHours - alarm activated"
::= { notifications 33556776 }

tMaintenanceTimer2RunHoursL1Disappeared	NOTIFICATION-TYPE
	OBJECTS	{tControllerName, tSerNum, tTrapText}
	STATUS	current
	DESCRIPTION	"Protection 1. level - Maintenance Timer 2 RunHours - alarm disappeared"
::= { notifications 33556777 }

tMaintenanceTimer2RunHoursL1AlarmReset	NOTIFICATION-TYPE
	OBJECTS	{tControllerName, tSerNum, tTrapText}
	STATUS	current
	DESCRIPTION	"Protection 1. level - Maintenance Timer 2 RunHours - alarm reset"
::= { notifications 33556778 }

tMaintenanceTimer2RunHoursL2Activated	NOTIFICATION-TYPE
	OBJECTS	{tControllerName, tSerNum, tTrapText}
	STATUS	current
	DESCRIPTION	"Protection 2. level - Maintenance Timer 2 RunHours - alarm activated"
::= { notifications 167774504 }

tMaintenanceTimer2RunHoursL2Disappeared	NOTIFICATION-TYPE
	OBJECTS	{tControllerName, tSerNum, tTrapText}
	STATUS	current
	DESCRIPTION	"Protection 2. level - Maintenance Timer 2 RunHours - alarm disappeared"
::= { notifications 167774505 }

tMaintenanceTimer2RunHoursL2AlarmReset	NOTIFICATION-TYPE
	OBJECTS	{tControllerName, tSerNum, tTrapText}
	STATUS	current
	DESCRIPTION	"Protection 2. level - Maintenance Timer 2 RunHours - alarm reset"
::= { notifications 167774506 }

tMaintenanceTimer3RunHoursL1Activated	NOTIFICATION-TYPE
	OBJECTS	{tControllerName, tSerNum, tTrapText}
	STATUS	current
	DESCRIPTION	"Protection 1. level - Maintenance Timer 3 RunHours - alarm activated"
::= { notifications 33556780 }

tMaintenanceTimer3RunHoursL1Disappeared	NOTIFICATION-TYPE
	OBJECTS	{tControllerName, tSerNum, tTrapText}
	STATUS	current
	DESCRIPTION	"Protection 1. level - Maintenance Timer 3 RunHours - alarm disappeared"
::= { notifications 33556781 }

tMaintenanceTimer3RunHoursL1AlarmReset	NOTIFICATION-TYPE
	OBJECTS	{tControllerName, tSerNum, tTrapText}
	STATUS	current
	DESCRIPTION	"Protection 1. level - Maintenance Timer 3 RunHours - alarm reset"
::= { notifications 33556782 }

tMaintenanceTimer3RunHoursL2Activated	NOTIFICATION-TYPE
	OBJECTS	{tControllerName, tSerNum, tTrapText}
	STATUS	current
	DESCRIPTION	"Protection 2. level - Maintenance Timer 3 RunHours - alarm activated"
::= { notifications 167774508 }

tMaintenanceTimer3RunHoursL2Disappeared	NOTIFICATION-TYPE
	OBJECTS	{tControllerName, tSerNum, tTrapText}
	STATUS	current
	DESCRIPTION	"Protection 2. level - Maintenance Timer 3 RunHours - alarm disappeared"
::= { notifications 167774509 }

tMaintenanceTimer3RunHoursL2AlarmReset	NOTIFICATION-TYPE
	OBJECTS	{tControllerName, tSerNum, tTrapText}
	STATUS	current
	DESCRIPTION	"Protection 2. level - Maintenance Timer 3 RunHours - alarm reset"
::= { notifications 167774510 }

tMaintenanceTimer4RunHoursL1Activated	NOTIFICATION-TYPE
	OBJECTS	{tControllerName, tSerNum, tTrapText}
	STATUS	current
	DESCRIPTION	"Protection 1. level - Maintenance Timer 4 RunHours - alarm activated"
::= { notifications 33560504 }

tMaintenanceTimer4RunHoursL1Disappeared	NOTIFICATION-TYPE
	OBJECTS	{tControllerName, tSerNum, tTrapText}
	STATUS	current
	DESCRIPTION	"Protection 1. level - Maintenance Timer 4 RunHours - alarm disappeared"
::= { notifications 33560505 }

tMaintenanceTimer4RunHoursL1AlarmReset	NOTIFICATION-TYPE
	OBJECTS	{tControllerName, tSerNum, tTrapText}
	STATUS	current
	DESCRIPTION	"Protection 1. level - Maintenance Timer 4 RunHours - alarm reset"
::= { notifications 33560506 }

tMaintenanceTimer4RunHoursL2Activated	NOTIFICATION-TYPE
	OBJECTS	{tControllerName, tSerNum, tTrapText}
	STATUS	current
	DESCRIPTION	"Protection 2. level - Maintenance Timer 4 RunHours - alarm activated"
::= { notifications 167778232 }

tMaintenanceTimer4RunHoursL2Disappeared	NOTIFICATION-TYPE
	OBJECTS	{tControllerName, tSerNum, tTrapText}
	STATUS	current
	DESCRIPTION	"Protection 2. level - Maintenance Timer 4 RunHours - alarm disappeared"
::= { notifications 167778233 }

tMaintenanceTimer4RunHoursL2AlarmReset	NOTIFICATION-TYPE
	OBJECTS	{tControllerName, tSerNum, tTrapText}
	STATUS	current
	DESCRIPTION	"Protection 2. level - Maintenance Timer 4 RunHours - alarm reset"
::= { notifications 167778234 }

tMaintenanceTimer1IntervalL1Activated	NOTIFICATION-TYPE
	OBJECTS	{tControllerName, tSerNum, tTrapText}
	STATUS	current
	DESCRIPTION	"Protection 1. level - Maintenance Timer 1 Interval - alarm activated"
::= { notifications 33558720 }

tMaintenanceTimer1IntervalL1Disappeared	NOTIFICATION-TYPE
	OBJECTS	{tControllerName, tSerNum, tTrapText}
	STATUS	current
	DESCRIPTION	"Protection 1. level - Maintenance Timer 1 Interval - alarm disappeared"
::= { notifications 33558721 }

tMaintenanceTimer1IntervalL1AlarmReset	NOTIFICATION-TYPE
	OBJECTS	{tControllerName, tSerNum, tTrapText}
	STATUS	current
	DESCRIPTION	"Protection 1. level - Maintenance Timer 1 Interval - alarm reset"
::= { notifications 33558722 }

tMaintenanceTimer1IntervalL2Activated	NOTIFICATION-TYPE
	OBJECTS	{tControllerName, tSerNum, tTrapText}
	STATUS	current
	DESCRIPTION	"Protection 2. level - Maintenance Timer 1 Interval - alarm activated"
::= { notifications 167776448 }

tMaintenanceTimer1IntervalL2Disappeared	NOTIFICATION-TYPE
	OBJECTS	{tControllerName, tSerNum, tTrapText}
	STATUS	current
	DESCRIPTION	"Protection 2. level - Maintenance Timer 1 Interval - alarm disappeared"
::= { notifications 167776449 }

tMaintenanceTimer1IntervalL2AlarmReset	NOTIFICATION-TYPE
	OBJECTS	{tControllerName, tSerNum, tTrapText}
	STATUS	current
	DESCRIPTION	"Protection 2. level - Maintenance Timer 1 Interval - alarm reset"
::= { notifications 167776450 }

tMaintenanceTimer2IntervalL1Activated	NOTIFICATION-TYPE
	OBJECTS	{tControllerName, tSerNum, tTrapText}
	STATUS	current
	DESCRIPTION	"Protection 1. level - Maintenance Timer 2 Interval - alarm activated"
::= { notifications 33558724 }

tMaintenanceTimer2IntervalL1Disappeared	NOTIFICATION-TYPE
	OBJECTS	{tControllerName, tSerNum, tTrapText}
	STATUS	current
	DESCRIPTION	"Protection 1. level - Maintenance Timer 2 Interval - alarm disappeared"
::= { notifications 33558725 }

tMaintenanceTimer2IntervalL1AlarmReset	NOTIFICATION-TYPE
	OBJECTS	{tControllerName, tSerNum, tTrapText}
	STATUS	current
	DESCRIPTION	"Protection 1. level - Maintenance Timer 2 Interval - alarm reset"
::= { notifications 33558726 }

tMaintenanceTimer2IntervalL2Activated	NOTIFICATION-TYPE
	OBJECTS	{tControllerName, tSerNum, tTrapText}
	STATUS	current
	DESCRIPTION	"Protection 2. level - Maintenance Timer 2 Interval - alarm activated"
::= { notifications 167776452 }

tMaintenanceTimer2IntervalL2Disappeared	NOTIFICATION-TYPE
	OBJECTS	{tControllerName, tSerNum, tTrapText}
	STATUS	current
	DESCRIPTION	"Protection 2. level - Maintenance Timer 2 Interval - alarm disappeared"
::= { notifications 167776453 }

tMaintenanceTimer2IntervalL2AlarmReset	NOTIFICATION-TYPE
	OBJECTS	{tControllerName, tSerNum, tTrapText}
	STATUS	current
	DESCRIPTION	"Protection 2. level - Maintenance Timer 2 Interval - alarm reset"
::= { notifications 167776454 }

tMaintenanceTimer3IntervalL1Activated	NOTIFICATION-TYPE
	OBJECTS	{tControllerName, tSerNum, tTrapText}
	STATUS	current
	DESCRIPTION	"Protection 1. level - Maintenance Timer 3 Interval - alarm activated"
::= { notifications 33558728 }

tMaintenanceTimer3IntervalL1Disappeared	NOTIFICATION-TYPE
	OBJECTS	{tControllerName, tSerNum, tTrapText}
	STATUS	current
	DESCRIPTION	"Protection 1. level - Maintenance Timer 3 Interval - alarm disappeared"
::= { notifications 33558729 }

tMaintenanceTimer3IntervalL1AlarmReset	NOTIFICATION-TYPE
	OBJECTS	{tControllerName, tSerNum, tTrapText}
	STATUS	current
	DESCRIPTION	"Protection 1. level - Maintenance Timer 3 Interval - alarm reset"
::= { notifications 33558730 }

tMaintenanceTimer3IntervalL2Activated	NOTIFICATION-TYPE
	OBJECTS	{tControllerName, tSerNum, tTrapText}
	STATUS	current
	DESCRIPTION	"Protection 2. level - Maintenance Timer 3 Interval - alarm activated"
::= { notifications 167776456 }

tMaintenanceTimer3IntervalL2Disappeared	NOTIFICATION-TYPE
	OBJECTS	{tControllerName, tSerNum, tTrapText}
	STATUS	current
	DESCRIPTION	"Protection 2. level - Maintenance Timer 3 Interval - alarm disappeared"
::= { notifications 167776457 }

tMaintenanceTimer3IntervalL2AlarmReset	NOTIFICATION-TYPE
	OBJECTS	{tControllerName, tSerNum, tTrapText}
	STATUS	current
	DESCRIPTION	"Protection 2. level - Maintenance Timer 3 Interval - alarm reset"
::= { notifications 167776458 }

tMaintenanceTimer4IntervalL1Activated	NOTIFICATION-TYPE
	OBJECTS	{tControllerName, tSerNum, tTrapText}
	STATUS	current
	DESCRIPTION	"Protection 1. level - Maintenance Timer 4 Interval - alarm activated"
::= { notifications 33560508 }

tMaintenanceTimer4IntervalL1Disappeared	NOTIFICATION-TYPE
	OBJECTS	{tControllerName, tSerNum, tTrapText}
	STATUS	current
	DESCRIPTION	"Protection 1. level - Maintenance Timer 4 Interval - alarm disappeared"
::= { notifications 33560509 }

tMaintenanceTimer4IntervalL1AlarmReset	NOTIFICATION-TYPE
	OBJECTS	{tControllerName, tSerNum, tTrapText}
	STATUS	current
	DESCRIPTION	"Protection 1. level - Maintenance Timer 4 Interval - alarm reset"
::= { notifications 33560510 }

tMaintenanceTimer4IntervalL2Activated	NOTIFICATION-TYPE
	OBJECTS	{tControllerName, tSerNum, tTrapText}
	STATUS	current
	DESCRIPTION	"Protection 2. level - Maintenance Timer 4 Interval - alarm activated"
::= { notifications 167778236 }

tMaintenanceTimer4IntervalL2Disappeared	NOTIFICATION-TYPE
	OBJECTS	{tControllerName, tSerNum, tTrapText}
	STATUS	current
	DESCRIPTION	"Protection 2. level - Maintenance Timer 4 Interval - alarm disappeared"
::= { notifications 167778237 }

tMaintenanceTimer4IntervalL2AlarmReset	NOTIFICATION-TYPE
	OBJECTS	{tControllerName, tSerNum, tTrapText}
	STATUS	current
	DESCRIPTION	"Protection 2. level - Maintenance Timer 4 Interval - alarm reset"
::= { notifications 167778238 }

tStartFailL2Activated	NOTIFICATION-TYPE
	OBJECTS	{tControllerName, tSerNum, tTrapText}
	STATUS	current
	DESCRIPTION	"Protection 2. level - Start Fail - alarm activated"
::= { notifications 167772380 }

tStartFailL2Disappeared	NOTIFICATION-TYPE
	OBJECTS	{tControllerName, tSerNum, tTrapText}
	STATUS	current
	DESCRIPTION	"Protection 2. level - Start Fail - alarm disappeared"
::= { notifications 167772381 }

tStartFailL2AlarmReset	NOTIFICATION-TYPE
	OBJECTS	{tControllerName, tSerNum, tTrapText}
	STATUS	current
	DESCRIPTION	"Protection 2. level - Start Fail - alarm reset"
::= { notifications 167772382 }

tMCBFailL1Activated	NOTIFICATION-TYPE
	OBJECTS	{tControllerName, tSerNum, tTrapText}
	STATUS	current
	DESCRIPTION	"Protection 1. level - MCB Fail - alarm activated"
::= { notifications 33554792 }

tMCBFailL1Disappeared	NOTIFICATION-TYPE
	OBJECTS	{tControllerName, tSerNum, tTrapText}
	STATUS	current
	DESCRIPTION	"Protection 1. level - MCB Fail - alarm disappeared"
::= { notifications 33554793 }

tMCBFailL1AlarmReset	NOTIFICATION-TYPE
	OBJECTS	{tControllerName, tSerNum, tTrapText}
	STATUS	current
	DESCRIPTION	"Protection 1. level - MCB Fail - alarm reset"
::= { notifications 33554794 }

tMCBFailToOpenL1Activated	NOTIFICATION-TYPE
	OBJECTS	{tControllerName, tSerNum, tTrapText}
	STATUS	current
	DESCRIPTION	"Protection 1. level - MCB Fail To Open - alarm activated"
::= { notifications 33560640 }

tMCBFailToOpenL1Disappeared	NOTIFICATION-TYPE
	OBJECTS	{tControllerName, tSerNum, tTrapText}
	STATUS	current
	DESCRIPTION	"Protection 1. level - MCB Fail To Open - alarm disappeared"
::= { notifications 33560641 }

tMCBFailToOpenL1AlarmReset	NOTIFICATION-TYPE
	OBJECTS	{tControllerName, tSerNum, tTrapText}
	STATUS	current
	DESCRIPTION	"Protection 1. level - MCB Fail To Open - alarm reset"
::= { notifications 33560642 }

tMCBFailToCloseL1Activated	NOTIFICATION-TYPE
	OBJECTS	{tControllerName, tSerNum, tTrapText}
	STATUS	current
	DESCRIPTION	"Protection 1. level - MCB Fail To Close - alarm activated"
::= { notifications 33560644 }

tMCBFailToCloseL1Disappeared	NOTIFICATION-TYPE
	OBJECTS	{tControllerName, tSerNum, tTrapText}
	STATUS	current
	DESCRIPTION	"Protection 1. level - MCB Fail To Close - alarm disappeared"
::= { notifications 33560645 }

tMCBFailToCloseL1AlarmReset	NOTIFICATION-TYPE
	OBJECTS	{tControllerName, tSerNum, tTrapText}
	STATUS	current
	DESCRIPTION	"Protection 1. level - MCB Fail To Close - alarm reset"
::= { notifications 33560646 }

tBCBFailL2Activated	NOTIFICATION-TYPE
	OBJECTS	{tControllerName, tSerNum, tTrapText}
	STATUS	current
	DESCRIPTION	"Protection 2. level - BCB Fail - alarm activated"
::= { notifications 167772524 }

tBCBFailL2Disappeared	NOTIFICATION-TYPE
	OBJECTS	{tControllerName, tSerNum, tTrapText}
	STATUS	current
	DESCRIPTION	"Protection 2. level - BCB Fail - alarm disappeared"
::= { notifications 167772525 }

tBCBFailL2AlarmReset	NOTIFICATION-TYPE
	OBJECTS	{tControllerName, tSerNum, tTrapText}
	STATUS	current
	DESCRIPTION	"Protection 2. level - BCB Fail - alarm reset"
::= { notifications 167772526 }

tBCBFailToOpenL2Activated	NOTIFICATION-TYPE
	OBJECTS	{tControllerName, tSerNum, tTrapText}
	STATUS	current
	DESCRIPTION	"Protection 2. level - BCB Fail To Open - alarm activated"
::= { notifications 167778376 }

tBCBFailToOpenL2Disappeared	NOTIFICATION-TYPE
	OBJECTS	{tControllerName, tSerNum, tTrapText}
	STATUS	current
	DESCRIPTION	"Protection 2. level - BCB Fail To Open - alarm disappeared"
::= { notifications 167778377 }

tBCBFailToOpenL2AlarmReset	NOTIFICATION-TYPE
	OBJECTS	{tControllerName, tSerNum, tTrapText}
	STATUS	current
	DESCRIPTION	"Protection 2. level - BCB Fail To Open - alarm reset"
::= { notifications 167778378 }

tBCBFailToCloseL2Activated	NOTIFICATION-TYPE
	OBJECTS	{tControllerName, tSerNum, tTrapText}
	STATUS	current
	DESCRIPTION	"Protection 2. level - BCB Fail To Close - alarm activated"
::= { notifications 167778380 }

tBCBFailToCloseL2Disappeared	NOTIFICATION-TYPE
	OBJECTS	{tControllerName, tSerNum, tTrapText}
	STATUS	current
	DESCRIPTION	"Protection 2. level - BCB Fail To Close - alarm disappeared"
::= { notifications 167778381 }

tBCBFailToCloseL2AlarmReset	NOTIFICATION-TYPE
	OBJECTS	{tControllerName, tSerNum, tTrapText}
	STATUS	current
	DESCRIPTION	"Protection 2. level - BCB Fail To Close - alarm reset"
::= { notifications 167778382 }

tBCBSecondaryFailL2Activated	NOTIFICATION-TYPE
	OBJECTS	{tControllerName, tSerNum, tTrapText}
	STATUS	current
	DESCRIPTION	"Protection 2. level - BCB Secondary Fail - alarm activated"
::= { notifications 167773964 }

tBCBSecondaryFailL2Disappeared	NOTIFICATION-TYPE
	OBJECTS	{tControllerName, tSerNum, tTrapText}
	STATUS	current
	DESCRIPTION	"Protection 2. level - BCB Secondary Fail - alarm disappeared"
::= { notifications 167773965 }

tBCBSecondaryFailL2AlarmReset	NOTIFICATION-TYPE
	OBJECTS	{tControllerName, tSerNum, tTrapText}
	STATUS	current
	DESCRIPTION	"Protection 2. level - BCB Secondary Fail - alarm reset"
::= { notifications 167773966 }

tBCBSecondaryFailToOpenL2Activated	NOTIFICATION-TYPE
	OBJECTS	{tControllerName, tSerNum, tTrapText}
	STATUS	current
	DESCRIPTION	"Protection 2. level - BCB Secondary Fail To Open - alarm activated"
::= { notifications 167778384 }

tBCBSecondaryFailToOpenL2Disappeared	NOTIFICATION-TYPE
	OBJECTS	{tControllerName, tSerNum, tTrapText}
	STATUS	current
	DESCRIPTION	"Protection 2. level - BCB Secondary Fail To Open - alarm disappeared"
::= { notifications 167778385 }

tBCBSecondaryFailToOpenL2AlarmReset	NOTIFICATION-TYPE
	OBJECTS	{tControllerName, tSerNum, tTrapText}
	STATUS	current
	DESCRIPTION	"Protection 2. level - BCB Secondary Fail To Open - alarm reset"
::= { notifications 167778386 }

tBCBSecondaryFailToCloseL2Activated	NOTIFICATION-TYPE
	OBJECTS	{tControllerName, tSerNum, tTrapText}
	STATUS	current
	DESCRIPTION	"Protection 2. level - BCB Secondary Fail To Close - alarm activated"
::= { notifications 167778388 }

tBCBSecondaryFailToCloseL2Disappeared	NOTIFICATION-TYPE
	OBJECTS	{tControllerName, tSerNum, tTrapText}
	STATUS	current
	DESCRIPTION	"Protection 2. level - BCB Secondary Fail To Close - alarm disappeared"
::= { notifications 167778389 }

tBCBSecondaryFailToCloseL2AlarmReset	NOTIFICATION-TYPE
	OBJECTS	{tControllerName, tSerNum, tTrapText}
	STATUS	current
	DESCRIPTION	"Protection 2. level - BCB Secondary Fail To Close - alarm reset"
::= { notifications 167778390 }

tPVCBFailL1Activated	NOTIFICATION-TYPE
	OBJECTS	{tControllerName, tSerNum, tTrapText}
	STATUS	current
	DESCRIPTION	"Protection 1. level - PVCB Fail - alarm activated"
::= { notifications 33560788 }

tPVCBFailL1Disappeared	NOTIFICATION-TYPE
	OBJECTS	{tControllerName, tSerNum, tTrapText}
	STATUS	current
	DESCRIPTION	"Protection 1. level - PVCB Fail - alarm disappeared"
::= { notifications 33560789 }

tPVCBFailL1AlarmReset	NOTIFICATION-TYPE
	OBJECTS	{tControllerName, tSerNum, tTrapText}
	STATUS	current
	DESCRIPTION	"Protection 1. level - PVCB Fail - alarm reset"
::= { notifications 33560790 }

tPVCBFailToOpenL1Activated	NOTIFICATION-TYPE
	OBJECTS	{tControllerName, tSerNum, tTrapText}
	STATUS	current
	DESCRIPTION	"Protection 1. level - PVCB Fail To Open - alarm activated"
::= { notifications 33560792 }

tPVCBFailToOpenL1Disappeared	NOTIFICATION-TYPE
	OBJECTS	{tControllerName, tSerNum, tTrapText}
	STATUS	current
	DESCRIPTION	"Protection 1. level - PVCB Fail To Open - alarm disappeared"
::= { notifications 33560793 }

tPVCBFailToOpenL1AlarmReset	NOTIFICATION-TYPE
	OBJECTS	{tControllerName, tSerNum, tTrapText}
	STATUS	current
	DESCRIPTION	"Protection 1. level - PVCB Fail To Open - alarm reset"
::= { notifications 33560794 }

tPVCBFailToCloseL1Activated	NOTIFICATION-TYPE
	OBJECTS	{tControllerName, tSerNum, tTrapText}
	STATUS	current
	DESCRIPTION	"Protection 1. level - PVCB Fail To Close - alarm activated"
::= { notifications 33560796 }

tPVCBFailToCloseL1Disappeared	NOTIFICATION-TYPE
	OBJECTS	{tControllerName, tSerNum, tTrapText}
	STATUS	current
	DESCRIPTION	"Protection 1. level - PVCB Fail To Close - alarm disappeared"
::= { notifications 33560797 }

tPVCBFailToCloseL1AlarmReset	NOTIFICATION-TYPE
	OBJECTS	{tControllerName, tSerNum, tTrapText}
	STATUS	current
	DESCRIPTION	"Protection 1. level - PVCB Fail To Close - alarm reset"
::= { notifications 33560798 }

tBESSGtGtVL1NL2Activated	NOTIFICATION-TYPE
	OBJECTS	{tControllerName, tSerNum, tTrapText}
	STATUS	current
	DESCRIPTION	"Protection 2. level - BESS >>V L1-N - alarm activated"
::= { notifications 167776552 }

tBESSGtGtVL1NL2Disappeared	NOTIFICATION-TYPE
	OBJECTS	{tControllerName, tSerNum, tTrapText}
	STATUS	current
	DESCRIPTION	"Protection 2. level - BESS >>V L1-N - alarm disappeared"
::= { notifications 167776553 }

tBESSGtGtVL1NL2AlarmReset	NOTIFICATION-TYPE
	OBJECTS	{tControllerName, tSerNum, tTrapText}
	STATUS	current
	DESCRIPTION	"Protection 2. level - BESS >>V L1-N - alarm reset"
::= { notifications 167776554 }

tBESSGtGtVL2NL2Activated	NOTIFICATION-TYPE
	OBJECTS	{tControllerName, tSerNum, tTrapText}
	STATUS	current
	DESCRIPTION	"Protection 2. level - BESS >>V L2-N - alarm activated"
::= { notifications 167776556 }

tBESSGtGtVL2NL2Disappeared	NOTIFICATION-TYPE
	OBJECTS	{tControllerName, tSerNum, tTrapText}
	STATUS	current
	DESCRIPTION	"Protection 2. level - BESS >>V L2-N - alarm disappeared"
::= { notifications 167776557 }

tBESSGtGtVL2NL2AlarmReset	NOTIFICATION-TYPE
	OBJECTS	{tControllerName, tSerNum, tTrapText}
	STATUS	current
	DESCRIPTION	"Protection 2. level - BESS >>V L2-N - alarm reset"
::= { notifications 167776558 }

tBESSGtGtVL3NL2Activated	NOTIFICATION-TYPE
	OBJECTS	{tControllerName, tSerNum, tTrapText}
	STATUS	current
	DESCRIPTION	"Protection 2. level - BESS >>V L3-N - alarm activated"
::= { notifications 167776560 }

tBESSGtGtVL3NL2Disappeared	NOTIFICATION-TYPE
	OBJECTS	{tControllerName, tSerNum, tTrapText}
	STATUS	current
	DESCRIPTION	"Protection 2. level - BESS >>V L3-N - alarm disappeared"
::= { notifications 167776561 }

tBESSGtGtVL3NL2AlarmReset	NOTIFICATION-TYPE
	OBJECTS	{tControllerName, tSerNum, tTrapText}
	STATUS	current
	DESCRIPTION	"Protection 2. level - BESS >>V L3-N - alarm reset"
::= { notifications 167776562 }

tBESSGtGtVL1L2L2Activated	NOTIFICATION-TYPE
	OBJECTS	{tControllerName, tSerNum, tTrapText}
	STATUS	current
	DESCRIPTION	"Protection 2. level - BESS >>V L1-L2 - alarm activated"
::= { notifications 167776564 }

tBESSGtGtVL1L2L2Disappeared	NOTIFICATION-TYPE
	OBJECTS	{tControllerName, tSerNum, tTrapText}
	STATUS	current
	DESCRIPTION	"Protection 2. level - BESS >>V L1-L2 - alarm disappeared"
::= { notifications 167776565 }

tBESSGtGtVL1L2L2AlarmReset	NOTIFICATION-TYPE
	OBJECTS	{tControllerName, tSerNum, tTrapText}
	STATUS	current
	DESCRIPTION	"Protection 2. level - BESS >>V L1-L2 - alarm reset"
::= { notifications 167776566 }

tBESSGtGtVL2L3L2Activated	NOTIFICATION-TYPE
	OBJECTS	{tControllerName, tSerNum, tTrapText}
	STATUS	current
	DESCRIPTION	"Protection 2. level - BESS >>V L2-L3 - alarm activated"
::= { notifications 167776568 }

tBESSGtGtVL2L3L2Disappeared	NOTIFICATION-TYPE
	OBJECTS	{tControllerName, tSerNum, tTrapText}
	STATUS	current
	DESCRIPTION	"Protection 2. level - BESS >>V L2-L3 - alarm disappeared"
::= { notifications 167776569 }

tBESSGtGtVL2L3L2AlarmReset	NOTIFICATION-TYPE
	OBJECTS	{tControllerName, tSerNum, tTrapText}
	STATUS	current
	DESCRIPTION	"Protection 2. level - BESS >>V L2-L3 - alarm reset"
::= { notifications 167776570 }

tBESSGtGtVL3L1L2Activated	NOTIFICATION-TYPE
	OBJECTS	{tControllerName, tSerNum, tTrapText}
	STATUS	current
	DESCRIPTION	"Protection 2. level - BESS >>V L3-L1 - alarm activated"
::= { notifications 167776572 }

tBESSGtGtVL3L1L2Disappeared	NOTIFICATION-TYPE
	OBJECTS	{tControllerName, tSerNum, tTrapText}
	STATUS	current
	DESCRIPTION	"Protection 2. level - BESS >>V L3-L1 - alarm disappeared"
::= { notifications 167776573 }

tBESSGtGtVL3L1L2AlarmReset	NOTIFICATION-TYPE
	OBJECTS	{tControllerName, tSerNum, tTrapText}
	STATUS	current
	DESCRIPTION	"Protection 2. level - BESS >>V L3-L1 - alarm reset"
::= { notifications 167776574 }

tBESSGtVL1NL2Activated	NOTIFICATION-TYPE
	OBJECTS	{tControllerName, tSerNum, tTrapText}
	STATUS	current
	DESCRIPTION	"Protection 2. level - BESS >V L1-N - alarm activated"
::= { notifications 167772552 }

tBESSGtVL1NL2Disappeared	NOTIFICATION-TYPE
	OBJECTS	{tControllerName, tSerNum, tTrapText}
	STATUS	current
	DESCRIPTION	"Protection 2. level - BESS >V L1-N - alarm disappeared"
::= { notifications 167772553 }

tBESSGtVL1NL2AlarmReset	NOTIFICATION-TYPE
	OBJECTS	{tControllerName, tSerNum, tTrapText}
	STATUS	current
	DESCRIPTION	"Protection 2. level - BESS >V L1-N - alarm reset"
::= { notifications 167772554 }

tBESSGtVL2NL2Activated	NOTIFICATION-TYPE
	OBJECTS	{tControllerName, tSerNum, tTrapText}
	STATUS	current
	DESCRIPTION	"Protection 2. level - BESS >V L2-N - alarm activated"
::= { notifications 167772556 }

tBESSGtVL2NL2Disappeared	NOTIFICATION-TYPE
	OBJECTS	{tControllerName, tSerNum, tTrapText}
	STATUS	current
	DESCRIPTION	"Protection 2. level - BESS >V L2-N - alarm disappeared"
::= { notifications 167772557 }

tBESSGtVL2NL2AlarmReset	NOTIFICATION-TYPE
	OBJECTS	{tControllerName, tSerNum, tTrapText}
	STATUS	current
	DESCRIPTION	"Protection 2. level - BESS >V L2-N - alarm reset"
::= { notifications 167772558 }

tBESSGtVL3NL2Activated	NOTIFICATION-TYPE
	OBJECTS	{tControllerName, tSerNum, tTrapText}
	STATUS	current
	DESCRIPTION	"Protection 2. level - BESS >V L3-N - alarm activated"
::= { notifications 167772560 }

tBESSGtVL3NL2Disappeared	NOTIFICATION-TYPE
	OBJECTS	{tControllerName, tSerNum, tTrapText}
	STATUS	current
	DESCRIPTION	"Protection 2. level - BESS >V L3-N - alarm disappeared"
::= { notifications 167772561 }

tBESSGtVL3NL2AlarmReset	NOTIFICATION-TYPE
	OBJECTS	{tControllerName, tSerNum, tTrapText}
	STATUS	current
	DESCRIPTION	"Protection 2. level - BESS >V L3-N - alarm reset"
::= { notifications 167772562 }

tBESSGtVL1L2L2Activated	NOTIFICATION-TYPE
	OBJECTS	{tControllerName, tSerNum, tTrapText}
	STATUS	current
	DESCRIPTION	"Protection 2. level - BESS >V L1-L2 - alarm activated"
::= { notifications 167772588 }

tBESSGtVL1L2L2Disappeared	NOTIFICATION-TYPE
	OBJECTS	{tControllerName, tSerNum, tTrapText}
	STATUS	current
	DESCRIPTION	"Protection 2. level - BESS >V L1-L2 - alarm disappeared"
::= { notifications 167772589 }

tBESSGtVL1L2L2AlarmReset	NOTIFICATION-TYPE
	OBJECTS	{tControllerName, tSerNum, tTrapText}
	STATUS	current
	DESCRIPTION	"Protection 2. level - BESS >V L1-L2 - alarm reset"
::= { notifications 167772590 }

tBESSGtVL2L3L2Activated	NOTIFICATION-TYPE
	OBJECTS	{tControllerName, tSerNum, tTrapText}
	STATUS	current
	DESCRIPTION	"Protection 2. level - BESS >V L2-L3 - alarm activated"
::= { notifications 167772592 }

tBESSGtVL2L3L2Disappeared	NOTIFICATION-TYPE
	OBJECTS	{tControllerName, tSerNum, tTrapText}
	STATUS	current
	DESCRIPTION	"Protection 2. level - BESS >V L2-L3 - alarm disappeared"
::= { notifications 167772593 }

tBESSGtVL2L3L2AlarmReset	NOTIFICATION-TYPE
	OBJECTS	{tControllerName, tSerNum, tTrapText}
	STATUS	current
	DESCRIPTION	"Protection 2. level - BESS >V L2-L3 - alarm reset"
::= { notifications 167772594 }

tBESSGtVL3L1L2Activated	NOTIFICATION-TYPE
	OBJECTS	{tControllerName, tSerNum, tTrapText}
	STATUS	current
	DESCRIPTION	"Protection 2. level - BESS >V L3-L1 - alarm activated"
::= { notifications 167772596 }

tBESSGtVL3L1L2Disappeared	NOTIFICATION-TYPE
	OBJECTS	{tControllerName, tSerNum, tTrapText}
	STATUS	current
	DESCRIPTION	"Protection 2. level - BESS >V L3-L1 - alarm disappeared"
::= { notifications 167772597 }

tBESSGtVL3L1L2AlarmReset	NOTIFICATION-TYPE
	OBJECTS	{tControllerName, tSerNum, tTrapText}
	STATUS	current
	DESCRIPTION	"Protection 2. level - BESS >V L3-L1 - alarm reset"
::= { notifications 167772598 }

tBESSLtVL1NL2Activated	NOTIFICATION-TYPE
	OBJECTS	{tControllerName, tSerNum, tTrapText}
	STATUS	current
	DESCRIPTION	"Protection 2. level - BESS <V L1-N - alarm activated"
::= { notifications 167772540 }

tBESSLtVL1NL2Disappeared	NOTIFICATION-TYPE
	OBJECTS	{tControllerName, tSerNum, tTrapText}
	STATUS	current
	DESCRIPTION	"Protection 2. level - BESS <V L1-N - alarm disappeared"
::= { notifications 167772541 }

tBESSLtVL1NL2AlarmReset	NOTIFICATION-TYPE
	OBJECTS	{tControllerName, tSerNum, tTrapText}
	STATUS	current
	DESCRIPTION	"Protection 2. level - BESS <V L1-N - alarm reset"
::= { notifications 167772542 }

tBESSLtVL2NL2Activated	NOTIFICATION-TYPE
	OBJECTS	{tControllerName, tSerNum, tTrapText}
	STATUS	current
	DESCRIPTION	"Protection 2. level - BESS <V L2-N - alarm activated"
::= { notifications 167772544 }

tBESSLtVL2NL2Disappeared	NOTIFICATION-TYPE
	OBJECTS	{tControllerName, tSerNum, tTrapText}
	STATUS	current
	DESCRIPTION	"Protection 2. level - BESS <V L2-N - alarm disappeared"
::= { notifications 167772545 }

tBESSLtVL2NL2AlarmReset	NOTIFICATION-TYPE
	OBJECTS	{tControllerName, tSerNum, tTrapText}
	STATUS	current
	DESCRIPTION	"Protection 2. level - BESS <V L2-N - alarm reset"
::= { notifications 167772546 }

tBESSLtVL3NL2Activated	NOTIFICATION-TYPE
	OBJECTS	{tControllerName, tSerNum, tTrapText}
	STATUS	current
	DESCRIPTION	"Protection 2. level - BESS <V L3-N - alarm activated"
::= { notifications 167772548 }

tBESSLtVL3NL2Disappeared	NOTIFICATION-TYPE
	OBJECTS	{tControllerName, tSerNum, tTrapText}
	STATUS	current
	DESCRIPTION	"Protection 2. level - BESS <V L3-N - alarm disappeared"
::= { notifications 167772549 }

tBESSLtVL3NL2AlarmReset	NOTIFICATION-TYPE
	OBJECTS	{tControllerName, tSerNum, tTrapText}
	STATUS	current
	DESCRIPTION	"Protection 2. level - BESS <V L3-N - alarm reset"
::= { notifications 167772550 }

tBESSLtVL1L2L2Activated	NOTIFICATION-TYPE
	OBJECTS	{tControllerName, tSerNum, tTrapText}
	STATUS	current
	DESCRIPTION	"Protection 2. level - BESS <V L1-L2 - alarm activated"
::= { notifications 167772576 }

tBESSLtVL1L2L2Disappeared	NOTIFICATION-TYPE
	OBJECTS	{tControllerName, tSerNum, tTrapText}
	STATUS	current
	DESCRIPTION	"Protection 2. level - BESS <V L1-L2 - alarm disappeared"
::= { notifications 167772577 }

tBESSLtVL1L2L2AlarmReset	NOTIFICATION-TYPE
	OBJECTS	{tControllerName, tSerNum, tTrapText}
	STATUS	current
	DESCRIPTION	"Protection 2. level - BESS <V L1-L2 - alarm reset"
::= { notifications 167772578 }

tBESSLtVL2L3L2Activated	NOTIFICATION-TYPE
	OBJECTS	{tControllerName, tSerNum, tTrapText}
	STATUS	current
	DESCRIPTION	"Protection 2. level - BESS <V L2-L3 - alarm activated"
::= { notifications 167772580 }

tBESSLtVL2L3L2Disappeared	NOTIFICATION-TYPE
	OBJECTS	{tControllerName, tSerNum, tTrapText}
	STATUS	current
	DESCRIPTION	"Protection 2. level - BESS <V L2-L3 - alarm disappeared"
::= { notifications 167772581 }

tBESSLtVL2L3L2AlarmReset	NOTIFICATION-TYPE
	OBJECTS	{tControllerName, tSerNum, tTrapText}
	STATUS	current
	DESCRIPTION	"Protection 2. level - BESS <V L2-L3 - alarm reset"
::= { notifications 167772582 }

tBESSLtVL3L1L2Activated	NOTIFICATION-TYPE
	OBJECTS	{tControllerName, tSerNum, tTrapText}
	STATUS	current
	DESCRIPTION	"Protection 2. level - BESS <V L3-L1 - alarm activated"
::= { notifications 167772584 }

tBESSLtVL3L1L2Disappeared	NOTIFICATION-TYPE
	OBJECTS	{tControllerName, tSerNum, tTrapText}
	STATUS	current
	DESCRIPTION	"Protection 2. level - BESS <V L3-L1 - alarm disappeared"
::= { notifications 167772585 }

tBESSLtVL3L1L2AlarmReset	NOTIFICATION-TYPE
	OBJECTS	{tControllerName, tSerNum, tTrapText}
	STATUS	current
	DESCRIPTION	"Protection 2. level - BESS <V L3-L1 - alarm reset"
::= { notifications 167772586 }

tBESSVUnbalancePhPhL2Activated2	NOTIFICATION-TYPE
	OBJECTS	{tControllerName, tSerNum, tTrapText}
	STATUS	current
	DESCRIPTION	"Protection 2. level - BESS V Unbalance Ph-Ph - alarm activated"
::= { notifications 167774512 }

tBESSVUnbalancePhPhL2Disappeared2	NOTIFICATION-TYPE
	OBJECTS	{tControllerName, tSerNum, tTrapText}
	STATUS	current
	DESCRIPTION	"Protection 2. level - BESS V Unbalance Ph-Ph - alarm disappeared"
::= { notifications 167774513 }

tBESSVUnbalancePhPhL2AlarmReset2	NOTIFICATION-TYPE
	OBJECTS	{tControllerName, tSerNum, tTrapText}
	STATUS	current
	DESCRIPTION	"Protection 2. level - BESS V Unbalance Ph-Ph - alarm reset"
::= { notifications 167774514 }

tBESSVUnbalancePhNL2Activated2	NOTIFICATION-TYPE
	OBJECTS	{tControllerName, tSerNum, tTrapText}
	STATUS	current
	DESCRIPTION	"Protection 2. level - BESS V Unbalance Ph-N - alarm activated"
::= { notifications 167774516 }

tBESSVUnbalancePhNL2Disappeared2	NOTIFICATION-TYPE
	OBJECTS	{tControllerName, tSerNum, tTrapText}
	STATUS	current
	DESCRIPTION	"Protection 2. level - BESS V Unbalance Ph-N - alarm disappeared"
::= { notifications 167774517 }

tBESSVUnbalancePhNL2AlarmReset2	NOTIFICATION-TYPE
	OBJECTS	{tControllerName, tSerNum, tTrapText}
	STATUS	current
	DESCRIPTION	"Protection 2. level - BESS V Unbalance Ph-N - alarm reset"
::= { notifications 167774518 }

tBESSGtFL2Activated	NOTIFICATION-TYPE
	OBJECTS	{tControllerName, tSerNum, tTrapText}
	STATUS	current
	DESCRIPTION	"Protection 2. level - BESS >f - alarm activated"
::= { notifications 167772644 }

tBESSGtFL2Disappeared	NOTIFICATION-TYPE
	OBJECTS	{tControllerName, tSerNum, tTrapText}
	STATUS	current
	DESCRIPTION	"Protection 2. level - BESS >f - alarm disappeared"
::= { notifications 167772645 }

tBESSGtFL2AlarmReset	NOTIFICATION-TYPE
	OBJECTS	{tControllerName, tSerNum, tTrapText}
	STATUS	current
	DESCRIPTION	"Protection 2. level - BESS >f - alarm reset"
::= { notifications 167772646 }

tBESSLtFL2Activated	NOTIFICATION-TYPE
	OBJECTS	{tControllerName, tSerNum, tTrapText}
	STATUS	current
	DESCRIPTION	"Protection 2. level - BESS <f - alarm activated"
::= { notifications 167772640 }

tBESSLtFL2Disappeared	NOTIFICATION-TYPE
	OBJECTS	{tControllerName, tSerNum, tTrapText}
	STATUS	current
	DESCRIPTION	"Protection 2. level - BESS <f - alarm disappeared"
::= { notifications 167772641 }

tBESSLtFL2AlarmReset	NOTIFICATION-TYPE
	OBJECTS	{tControllerName, tSerNum, tTrapText}
	STATUS	current
	DESCRIPTION	"Protection 2. level - BESS <f - alarm reset"
::= { notifications 167772642 }

tBESSCurrentUnbalanceL2Activated2	NOTIFICATION-TYPE
	OBJECTS	{tControllerName, tSerNum, tTrapText}
	STATUS	current
	DESCRIPTION	"Protection 2. level - BESS Current Unbalance - alarm activated"
::= { notifications 167774524 }

tBESSCurrentUnbalanceL2Disappeared2	NOTIFICATION-TYPE
	OBJECTS	{tControllerName, tSerNum, tTrapText}
	STATUS	current
	DESCRIPTION	"Protection 2. level - BESS Current Unbalance - alarm disappeared"
::= { notifications 167774525 }

tBESSCurrentUnbalanceL2AlarmReset2	NOTIFICATION-TYPE
	OBJECTS	{tControllerName, tSerNum, tTrapText}
	STATUS	current
	DESCRIPTION	"Protection 2. level - BESS Current Unbalance - alarm reset"
::= { notifications 167774526 }

tQAmpUProtUm12L1Activated	NOTIFICATION-TYPE
	OBJECTS	{tControllerName, tSerNum, tTrapText}
	STATUS	current
	DESCRIPTION	"Protection 1. level - Q&U Prot - Um12 - alarm activated"
::= { notifications 33560664 }

tQAmpUProtUm12L1Disappeared	NOTIFICATION-TYPE
	OBJECTS	{tControllerName, tSerNum, tTrapText}
	STATUS	current
	DESCRIPTION	"Protection 1. level - Q&U Prot - Um12 - alarm disappeared"
::= { notifications 33560665 }

tQAmpUProtUm12L1AlarmReset	NOTIFICATION-TYPE
	OBJECTS	{tControllerName, tSerNum, tTrapText}
	STATUS	current
	DESCRIPTION	"Protection 1. level - Q&U Prot - Um12 - alarm reset"
::= { notifications 33560666 }

tQAmpUProtUm12L2Activated	NOTIFICATION-TYPE
	OBJECTS	{tControllerName, tSerNum, tTrapText}
	STATUS	current
	DESCRIPTION	"Protection 2. level - Q&U Prot - Um12 - alarm activated"
::= { notifications 167778392 }

tQAmpUProtUm12L2Disappeared	NOTIFICATION-TYPE
	OBJECTS	{tControllerName, tSerNum, tTrapText}
	STATUS	current
	DESCRIPTION	"Protection 2. level - Q&U Prot - Um12 - alarm disappeared"
::= { notifications 167778393 }

tQAmpUProtUm12L2AlarmReset	NOTIFICATION-TYPE
	OBJECTS	{tControllerName, tSerNum, tTrapText}
	STATUS	current
	DESCRIPTION	"Protection 2. level - Q&U Prot - Um12 - alarm reset"
::= { notifications 167778394 }

tQAmpUProtUm12SFActivated	NOTIFICATION-TYPE
	OBJECTS	{tControllerName, tSerNum, tTrapText}
	STATUS	current
	DESCRIPTION	"Protection Sensor Fail - Q&U Prot - Um12 - alarm activated"
::= { notifications 301996120 }

tQAmpUProtUm12SFDisappeared	NOTIFICATION-TYPE
	OBJECTS	{tControllerName, tSerNum, tTrapText}
	STATUS	current
	DESCRIPTION	"Protection Sensor Fail - Q&U Prot - Um12 - alarm disappeared"
::= { notifications 301996121 }

tQAmpUProtUm12SFAlarmReset	NOTIFICATION-TYPE
	OBJECTS	{tControllerName, tSerNum, tTrapText}
	STATUS	current
	DESCRIPTION	"Protection Sensor Fail - Q&U Prot - Um12 - alarm reset"
::= { notifications 301996122 }

tQAmpUProtUm23L1Activated	NOTIFICATION-TYPE
	OBJECTS	{tControllerName, tSerNum, tTrapText}
	STATUS	current
	DESCRIPTION	"Protection 1. level - Q&U Prot - Um23 - alarm activated"
::= { notifications 33560668 }

tQAmpUProtUm23L1Disappeared	NOTIFICATION-TYPE
	OBJECTS	{tControllerName, tSerNum, tTrapText}
	STATUS	current
	DESCRIPTION	"Protection 1. level - Q&U Prot - Um23 - alarm disappeared"
::= { notifications 33560669 }

tQAmpUProtUm23L1AlarmReset	NOTIFICATION-TYPE
	OBJECTS	{tControllerName, tSerNum, tTrapText}
	STATUS	current
	DESCRIPTION	"Protection 1. level - Q&U Prot - Um23 - alarm reset"
::= { notifications 33560670 }

tQAmpUProtUm23L2Activated	NOTIFICATION-TYPE
	OBJECTS	{tControllerName, tSerNum, tTrapText}
	STATUS	current
	DESCRIPTION	"Protection 2. level - Q&U Prot - Um23 - alarm activated"
::= { notifications 167778396 }

tQAmpUProtUm23L2Disappeared	NOTIFICATION-TYPE
	OBJECTS	{tControllerName, tSerNum, tTrapText}
	STATUS	current
	DESCRIPTION	"Protection 2. level - Q&U Prot - Um23 - alarm disappeared"
::= { notifications 167778397 }

tQAmpUProtUm23L2AlarmReset	NOTIFICATION-TYPE
	OBJECTS	{tControllerName, tSerNum, tTrapText}
	STATUS	current
	DESCRIPTION	"Protection 2. level - Q&U Prot - Um23 - alarm reset"
::= { notifications 167778398 }

tQAmpUProtUm23SFActivated	NOTIFICATION-TYPE
	OBJECTS	{tControllerName, tSerNum, tTrapText}
	STATUS	current
	DESCRIPTION	"Protection Sensor Fail - Q&U Prot - Um23 - alarm activated"
::= { notifications 301996124 }

tQAmpUProtUm23SFDisappeared	NOTIFICATION-TYPE
	OBJECTS	{tControllerName, tSerNum, tTrapText}
	STATUS	current
	DESCRIPTION	"Protection Sensor Fail - Q&U Prot - Um23 - alarm disappeared"
::= { notifications 301996125 }

tQAmpUProtUm23SFAlarmReset	NOTIFICATION-TYPE
	OBJECTS	{tControllerName, tSerNum, tTrapText}
	STATUS	current
	DESCRIPTION	"Protection Sensor Fail - Q&U Prot - Um23 - alarm reset"
::= { notifications 301996126 }

tQAmpUProtUm31L1Activated	NOTIFICATION-TYPE
	OBJECTS	{tControllerName, tSerNum, tTrapText}
	STATUS	current
	DESCRIPTION	"Protection 1. level - Q&U Prot - Um31 - alarm activated"
::= { notifications 33560672 }

tQAmpUProtUm31L1Disappeared	NOTIFICATION-TYPE
	OBJECTS	{tControllerName, tSerNum, tTrapText}
	STATUS	current
	DESCRIPTION	"Protection 1. level - Q&U Prot - Um31 - alarm disappeared"
::= { notifications 33560673 }

tQAmpUProtUm31L1AlarmReset	NOTIFICATION-TYPE
	OBJECTS	{tControllerName, tSerNum, tTrapText}
	STATUS	current
	DESCRIPTION	"Protection 1. level - Q&U Prot - Um31 - alarm reset"
::= { notifications 33560674 }

tQAmpUProtUm31L2Activated	NOTIFICATION-TYPE
	OBJECTS	{tControllerName, tSerNum, tTrapText}
	STATUS	current
	DESCRIPTION	"Protection 2. level - Q&U Prot - Um31 - alarm activated"
::= { notifications 167778400 }

tQAmpUProtUm31L2Disappeared	NOTIFICATION-TYPE
	OBJECTS	{tControllerName, tSerNum, tTrapText}
	STATUS	current
	DESCRIPTION	"Protection 2. level - Q&U Prot - Um31 - alarm disappeared"
::= { notifications 167778401 }

tQAmpUProtUm31L2AlarmReset	NOTIFICATION-TYPE
	OBJECTS	{tControllerName, tSerNum, tTrapText}
	STATUS	current
	DESCRIPTION	"Protection 2. level - Q&U Prot - Um31 - alarm reset"
::= { notifications 167778402 }

tQAmpUProtUm31SFActivated	NOTIFICATION-TYPE
	OBJECTS	{tControllerName, tSerNum, tTrapText}
	STATUS	current
	DESCRIPTION	"Protection Sensor Fail - Q&U Prot - Um31 - alarm activated"
::= { notifications 301996128 }

tQAmpUProtUm31SFDisappeared	NOTIFICATION-TYPE
	OBJECTS	{tControllerName, tSerNum, tTrapText}
	STATUS	current
	DESCRIPTION	"Protection Sensor Fail - Q&U Prot - Um31 - alarm disappeared"
::= { notifications 301996129 }

tQAmpUProtUm31SFAlarmReset	NOTIFICATION-TYPE
	OBJECTS	{tControllerName, tSerNum, tTrapText}
	STATUS	current
	DESCRIPTION	"Protection Sensor Fail - Q&U Prot - Um31 - alarm reset"
::= { notifications 301996130 }

tQAmpUProtQPartL1Activated	NOTIFICATION-TYPE
	OBJECTS	{tControllerName, tSerNum, tTrapText}
	STATUS	current
	DESCRIPTION	"Protection 1. level - Q&U Prot - Q part - alarm activated"
::= { notifications 33558940 }

tQAmpUProtQPartL1Disappeared	NOTIFICATION-TYPE
	OBJECTS	{tControllerName, tSerNum, tTrapText}
	STATUS	current
	DESCRIPTION	"Protection 1. level - Q&U Prot - Q part - alarm disappeared"
::= { notifications 33558941 }

tQAmpUProtQPartL1AlarmReset	NOTIFICATION-TYPE
	OBJECTS	{tControllerName, tSerNum, tTrapText}
	STATUS	current
	DESCRIPTION	"Protection 1. level - Q&U Prot - Q part - alarm reset"
::= { notifications 33558942 }

tQAmpUProtQPartL2Activated	NOTIFICATION-TYPE
	OBJECTS	{tControllerName, tSerNum, tTrapText}
	STATUS	current
	DESCRIPTION	"Protection 2. level - Q&U Prot - Q part - alarm activated"
::= { notifications 167776668 }

tQAmpUProtQPartL2Disappeared	NOTIFICATION-TYPE
	OBJECTS	{tControllerName, tSerNum, tTrapText}
	STATUS	current
	DESCRIPTION	"Protection 2. level - Q&U Prot - Q part - alarm disappeared"
::= { notifications 167776669 }

tQAmpUProtQPartL2AlarmReset	NOTIFICATION-TYPE
	OBJECTS	{tControllerName, tSerNum, tTrapText}
	STATUS	current
	DESCRIPTION	"Protection 2. level - Q&U Prot - Q part - alarm reset"
::= { notifications 167776670 }

tQAmpUProtQPartSFActivated	NOTIFICATION-TYPE
	OBJECTS	{tControllerName, tSerNum, tTrapText}
	STATUS	current
	DESCRIPTION	"Protection Sensor Fail - Q&U Prot - Q part - alarm activated"
::= { notifications 301994396 }

tQAmpUProtQPartSFDisappeared	NOTIFICATION-TYPE
	OBJECTS	{tControllerName, tSerNum, tTrapText}
	STATUS	current
	DESCRIPTION	"Protection Sensor Fail - Q&U Prot - Q part - alarm disappeared"
::= { notifications 301994397 }

tQAmpUProtQPartSFAlarmReset	NOTIFICATION-TYPE
	OBJECTS	{tControllerName, tSerNum, tTrapText}
	STATUS	current
	DESCRIPTION	"Protection Sensor Fail - Q&U Prot - Q part - alarm reset"
::= { notifications 301994398 }

tQAmpUProtectionL1Activated	NOTIFICATION-TYPE
	OBJECTS	{tControllerName, tSerNum, tTrapText}
	STATUS	current
	DESCRIPTION	"Protection 1. level - Q&U Protection - alarm activated"
::= { notifications 33556768 }

tQAmpUProtectionL1Disappeared	NOTIFICATION-TYPE
	OBJECTS	{tControllerName, tSerNum, tTrapText}
	STATUS	current
	DESCRIPTION	"Protection 1. level - Q&U Protection - alarm disappeared"
::= { notifications 33556769 }

tQAmpUProtectionL1AlarmReset	NOTIFICATION-TYPE
	OBJECTS	{tControllerName, tSerNum, tTrapText}
	STATUS	current
	DESCRIPTION	"Protection 1. level - Q&U Protection - alarm reset"
::= { notifications 33556770 }

tVRTProtectionTripL1Activated1	NOTIFICATION-TYPE
	OBJECTS	{tControllerName, tSerNum, tTrapText}
	STATUS	current
	DESCRIPTION	"Protection 1. level - VRT Protection Trip - alarm activated"
::= { notifications 33559004 }

tVRTProtectionTripL1Disappeared1	NOTIFICATION-TYPE
	OBJECTS	{tControllerName, tSerNum, tTrapText}
	STATUS	current
	DESCRIPTION	"Protection 1. level - VRT Protection Trip - alarm disappeared"
::= { notifications 33559005 }

tVRTProtectionTripL1AlarmReset1	NOTIFICATION-TYPE
	OBJECTS	{tControllerName, tSerNum, tTrapText}
	STATUS	current
	DESCRIPTION	"Protection 1. level - VRT Protection Trip - alarm reset"
::= { notifications 33559006 }

tVRTProtectionTripL1Activated2	NOTIFICATION-TYPE
	OBJECTS	{tControllerName, tSerNum, tTrapText}
	STATUS	current
	DESCRIPTION	"Protection 1. level - VRT Protection Trip - alarm activated"
::= { notifications 33558604 }

tVRTProtectionTripL1Disappeared2	NOTIFICATION-TYPE
	OBJECTS	{tControllerName, tSerNum, tTrapText}
	STATUS	current
	DESCRIPTION	"Protection 1. level - VRT Protection Trip - alarm disappeared"
::= { notifications 33558605 }

tVRTProtectionTripL1AlarmReset2	NOTIFICATION-TYPE
	OBJECTS	{tControllerName, tSerNum, tTrapText}
	STATUS	current
	DESCRIPTION	"Protection 1. level - VRT Protection Trip - alarm reset"
::= { notifications 33558606 }

tVRTProtectionTripL2Activated	NOTIFICATION-TYPE
	OBJECTS	{tControllerName, tSerNum, tTrapText}
	STATUS	current
	DESCRIPTION	"Protection 2. level - VRT Protection Trip - alarm activated"
::= { notifications 167776332 }

tVRTProtectionTripL2Disappeared	NOTIFICATION-TYPE
	OBJECTS	{tControllerName, tSerNum, tTrapText}
	STATUS	current
	DESCRIPTION	"Protection 2. level - VRT Protection Trip - alarm disappeared"
::= { notifications 167776333 }

tVRTProtectionTripL2AlarmReset	NOTIFICATION-TYPE
	OBJECTS	{tControllerName, tSerNum, tTrapText}
	STATUS	current
	DESCRIPTION	"Protection 2. level - VRT Protection Trip - alarm reset"
::= { notifications 167776334 }

tBESSPhRotationOppositeL1Activated	NOTIFICATION-TYPE
	OBJECTS	{tControllerName, tSerNum, tTrapText}
	STATUS	current
	DESCRIPTION	"Protection 1. level - BESS Ph Rotation Opposite - alarm activated"
::= { notifications 33555048 }

tBESSPhRotationOppositeL1Disappeared	NOTIFICATION-TYPE
	OBJECTS	{tControllerName, tSerNum, tTrapText}
	STATUS	current
	DESCRIPTION	"Protection 1. level - BESS Ph Rotation Opposite - alarm disappeared"
::= { notifications 33555049 }

tBESSPhRotationOppositeL1AlarmReset	NOTIFICATION-TYPE
	OBJECTS	{tControllerName, tSerNum, tTrapText}
	STATUS	current
	DESCRIPTION	"Protection 1. level - BESS Ph Rotation Opposite - alarm reset"
::= { notifications 33555050 }

tBESSPhL1InvertedL1Activated	NOTIFICATION-TYPE
	OBJECTS	{tControllerName, tSerNum, tTrapText}
	STATUS	current
	DESCRIPTION	"Protection 1. level - BESS Ph L1 Inverted - alarm activated"
::= { notifications 33558120 }

tBESSPhL1InvertedL1Disappeared	NOTIFICATION-TYPE
	OBJECTS	{tControllerName, tSerNum, tTrapText}
	STATUS	current
	DESCRIPTION	"Protection 1. level - BESS Ph L1 Inverted - alarm disappeared"
::= { notifications 33558121 }

tBESSPhL1InvertedL1AlarmReset	NOTIFICATION-TYPE
	OBJECTS	{tControllerName, tSerNum, tTrapText}
	STATUS	current
	DESCRIPTION	"Protection 1. level - BESS Ph L1 Inverted - alarm reset"
::= { notifications 33558122 }

tBESSPhL2InvertedL1Activated	NOTIFICATION-TYPE
	OBJECTS	{tControllerName, tSerNum, tTrapText}
	STATUS	current
	DESCRIPTION	"Protection 1. level - BESS Ph L2 Inverted - alarm activated"
::= { notifications 33558124 }

tBESSPhL2InvertedL1Disappeared	NOTIFICATION-TYPE
	OBJECTS	{tControllerName, tSerNum, tTrapText}
	STATUS	current
	DESCRIPTION	"Protection 1. level - BESS Ph L2 Inverted - alarm disappeared"
::= { notifications 33558125 }

tBESSPhL2InvertedL1AlarmReset	NOTIFICATION-TYPE
	OBJECTS	{tControllerName, tSerNum, tTrapText}
	STATUS	current
	DESCRIPTION	"Protection 1. level - BESS Ph L2 Inverted - alarm reset"
::= { notifications 33558126 }

tBESSPhL3InvertedL1Activated	NOTIFICATION-TYPE
	OBJECTS	{tControllerName, tSerNum, tTrapText}
	STATUS	current
	DESCRIPTION	"Protection 1. level - BESS Ph L3 Inverted - alarm activated"
::= { notifications 33558128 }

tBESSPhL3InvertedL1Disappeared	NOTIFICATION-TYPE
	OBJECTS	{tControllerName, tSerNum, tTrapText}
	STATUS	current
	DESCRIPTION	"Protection 1. level - BESS Ph L3 Inverted - alarm disappeared"
::= { notifications 33558129 }

tBESSPhL3InvertedL1AlarmReset	NOTIFICATION-TYPE
	OBJECTS	{tControllerName, tSerNum, tTrapText}
	STATUS	current
	DESCRIPTION	"Protection 1. level - BESS Ph L3 Inverted - alarm reset"
::= { notifications 33558130 }

tMainsPhRotationOppositeL1Activated	NOTIFICATION-TYPE
	OBJECTS	{tControllerName, tSerNum, tTrapText}
	STATUS	current
	DESCRIPTION	"Protection 1. level - Mains Ph Rotation Opposite - alarm activated"
::= { notifications 33555064 }

tMainsPhRotationOppositeL1Disappeared	NOTIFICATION-TYPE
	OBJECTS	{tControllerName, tSerNum, tTrapText}
	STATUS	current
	DESCRIPTION	"Protection 1. level - Mains Ph Rotation Opposite - alarm disappeared"
::= { notifications 33555065 }

tMainsPhRotationOppositeL1AlarmReset	NOTIFICATION-TYPE
	OBJECTS	{tControllerName, tSerNum, tTrapText}
	STATUS	current
	DESCRIPTION	"Protection 1. level - Mains Ph Rotation Opposite - alarm reset"
::= { notifications 33555066 }

tMainsPhL1InvertedL1Activated	NOTIFICATION-TYPE
	OBJECTS	{tControllerName, tSerNum, tTrapText}
	STATUS	current
	DESCRIPTION	"Protection 1. level - Mains Ph L1 Inverted - alarm activated"
::= { notifications 33558132 }

tMainsPhL1InvertedL1Disappeared	NOTIFICATION-TYPE
	OBJECTS	{tControllerName, tSerNum, tTrapText}
	STATUS	current
	DESCRIPTION	"Protection 1. level - Mains Ph L1 Inverted - alarm disappeared"
::= { notifications 33558133 }

tMainsPhL1InvertedL1AlarmReset	NOTIFICATION-TYPE
	OBJECTS	{tControllerName, tSerNum, tTrapText}
	STATUS	current
	DESCRIPTION	"Protection 1. level - Mains Ph L1 Inverted - alarm reset"
::= { notifications 33558134 }

tMainsPhL2InvertedL1Activated	NOTIFICATION-TYPE
	OBJECTS	{tControllerName, tSerNum, tTrapText}
	STATUS	current
	DESCRIPTION	"Protection 1. level - Mains Ph L2 Inverted - alarm activated"
::= { notifications 33558136 }

tMainsPhL2InvertedL1Disappeared	NOTIFICATION-TYPE
	OBJECTS	{tControllerName, tSerNum, tTrapText}
	STATUS	current
	DESCRIPTION	"Protection 1. level - Mains Ph L2 Inverted - alarm disappeared"
::= { notifications 33558137 }

tMainsPhL2InvertedL1AlarmReset	NOTIFICATION-TYPE
	OBJECTS	{tControllerName, tSerNum, tTrapText}
	STATUS	current
	DESCRIPTION	"Protection 1. level - Mains Ph L2 Inverted - alarm reset"
::= { notifications 33558138 }

tMainsPhL3InvertedL1Activated	NOTIFICATION-TYPE
	OBJECTS	{tControllerName, tSerNum, tTrapText}
	STATUS	current
	DESCRIPTION	"Protection 1. level - Mains Ph L3 Inverted - alarm activated"
::= { notifications 33558140 }

tMainsPhL3InvertedL1Disappeared	NOTIFICATION-TYPE
	OBJECTS	{tControllerName, tSerNum, tTrapText}
	STATUS	current
	DESCRIPTION	"Protection 1. level - Mains Ph L3 Inverted - alarm disappeared"
::= { notifications 33558141 }

tMainsPhL3InvertedL1AlarmReset	NOTIFICATION-TYPE
	OBJECTS	{tControllerName, tSerNum, tTrapText}
	STATUS	current
	DESCRIPTION	"Protection 1. level - Mains Ph L3 Inverted - alarm reset"
::= { notifications 33558142 }

tBusPhRotationOppositeL1Activated	NOTIFICATION-TYPE
	OBJECTS	{tControllerName, tSerNum, tTrapText}
	STATUS	current
	DESCRIPTION	"Protection 1. level - Bus Ph Rotation Opposite - alarm activated"
::= { notifications 33557820 }

tBusPhRotationOppositeL1Disappeared	NOTIFICATION-TYPE
	OBJECTS	{tControllerName, tSerNum, tTrapText}
	STATUS	current
	DESCRIPTION	"Protection 1. level - Bus Ph Rotation Opposite - alarm disappeared"
::= { notifications 33557821 }

tBusPhRotationOppositeL1AlarmReset	NOTIFICATION-TYPE
	OBJECTS	{tControllerName, tSerNum, tTrapText}
	STATUS	current
	DESCRIPTION	"Protection 1. level - Bus Ph Rotation Opposite - alarm reset"
::= { notifications 33557822 }

tBusPhL1InvertedL1Activated	NOTIFICATION-TYPE
	OBJECTS	{tControllerName, tSerNum, tTrapText}
	STATUS	current
	DESCRIPTION	"Protection 1. level - Bus Ph L1 Inverted - alarm activated"
::= { notifications 33558144 }

tBusPhL1InvertedL1Disappeared	NOTIFICATION-TYPE
	OBJECTS	{tControllerName, tSerNum, tTrapText}
	STATUS	current
	DESCRIPTION	"Protection 1. level - Bus Ph L1 Inverted - alarm disappeared"
::= { notifications 33558145 }

tBusPhL1InvertedL1AlarmReset	NOTIFICATION-TYPE
	OBJECTS	{tControllerName, tSerNum, tTrapText}
	STATUS	current
	DESCRIPTION	"Protection 1. level - Bus Ph L1 Inverted - alarm reset"
::= { notifications 33558146 }

tBusPhL2InvertedL1Activated	NOTIFICATION-TYPE
	OBJECTS	{tControllerName, tSerNum, tTrapText}
	STATUS	current
	DESCRIPTION	"Protection 1. level - Bus Ph L2 Inverted - alarm activated"
::= { notifications 33558148 }

tBusPhL2InvertedL1Disappeared	NOTIFICATION-TYPE
	OBJECTS	{tControllerName, tSerNum, tTrapText}
	STATUS	current
	DESCRIPTION	"Protection 1. level - Bus Ph L2 Inverted - alarm disappeared"
::= { notifications 33558149 }

tBusPhL2InvertedL1AlarmReset	NOTIFICATION-TYPE
	OBJECTS	{tControllerName, tSerNum, tTrapText}
	STATUS	current
	DESCRIPTION	"Protection 1. level - Bus Ph L2 Inverted - alarm reset"
::= { notifications 33558150 }

tBusPhL3InvertedL1Activated	NOTIFICATION-TYPE
	OBJECTS	{tControllerName, tSerNum, tTrapText}
	STATUS	current
	DESCRIPTION	"Protection 1. level - Bus Ph L3 Inverted - alarm activated"
::= { notifications 33558152 }

tBusPhL3InvertedL1Disappeared	NOTIFICATION-TYPE
	OBJECTS	{tControllerName, tSerNum, tTrapText}
	STATUS	current
	DESCRIPTION	"Protection 1. level - Bus Ph L3 Inverted - alarm disappeared"
::= { notifications 33558153 }

tBusPhL3InvertedL1AlarmReset	NOTIFICATION-TYPE
	OBJECTS	{tControllerName, tSerNum, tTrapText}
	STATUS	current
	DESCRIPTION	"Protection 1. level - Bus Ph L3 Inverted - alarm reset"
::= { notifications 33558154 }

tOverloadL1Activated	NOTIFICATION-TYPE
	OBJECTS	{tControllerName, tSerNum, tTrapText}
	STATUS	current
	DESCRIPTION	"Protection 1. level - Overload - alarm activated"
::= { notifications 33556808 }

tOverloadL1Disappeared	NOTIFICATION-TYPE
	OBJECTS	{tControllerName, tSerNum, tTrapText}
	STATUS	current
	DESCRIPTION	"Protection 1. level - Overload - alarm disappeared"
::= { notifications 33556809 }

tOverloadL1AlarmReset	NOTIFICATION-TYPE
	OBJECTS	{tControllerName, tSerNum, tTrapText}
	STATUS	current
	DESCRIPTION	"Protection 1. level - Overload - alarm reset"
::= { notifications 33556810 }

tIDMTOverloadL2Activated	NOTIFICATION-TYPE
	OBJECTS	{tControllerName, tSerNum, tTrapText}
	STATUS	current
	DESCRIPTION	"Protection 2. level - IDMT Overload - alarm activated"
::= { notifications 167772748 }

tIDMTOverloadL2Disappeared	NOTIFICATION-TYPE
	OBJECTS	{tControllerName, tSerNum, tTrapText}
	STATUS	current
	DESCRIPTION	"Protection 2. level - IDMT Overload - alarm disappeared"
::= { notifications 167772749 }

tIDMTOverloadL2AlarmReset	NOTIFICATION-TYPE
	OBJECTS	{tControllerName, tSerNum, tTrapText}
	STATUS	current
	DESCRIPTION	"Protection 2. level - IDMT Overload - alarm reset"
::= { notifications 167772750 }

tShortCircuitL2Activated	NOTIFICATION-TYPE
	OBJECTS	{tControllerName, tSerNum, tTrapText}
	STATUS	current
	DESCRIPTION	"Protection 2. level - Short Circuit - alarm activated"
::= { notifications 167774540 }

tShortCircuitL2Disappeared	NOTIFICATION-TYPE
	OBJECTS	{tControllerName, tSerNum, tTrapText}
	STATUS	current
	DESCRIPTION	"Protection 2. level - Short Circuit - alarm disappeared"
::= { notifications 167774541 }

tShortCircuitL2AlarmReset	NOTIFICATION-TYPE
	OBJECTS	{tControllerName, tSerNum, tTrapText}
	STATUS	current
	DESCRIPTION	"Protection 2. level - Short Circuit - alarm reset"
::= { notifications 167774542 }

tEarthFaultCurrentL2Activated	NOTIFICATION-TYPE
	OBJECTS	{tControllerName, tSerNum, tTrapText}
	STATUS	current
	DESCRIPTION	"Protection 2. level - Earth Fault Current - alarm activated"
::= { notifications 167774544 }

tEarthFaultCurrentL2Disappeared	NOTIFICATION-TYPE
	OBJECTS	{tControllerName, tSerNum, tTrapText}
	STATUS	current
	DESCRIPTION	"Protection 2. level - Earth Fault Current - alarm disappeared"
::= { notifications 167774545 }

tEarthFaultCurrentL2AlarmReset	NOTIFICATION-TYPE
	OBJECTS	{tControllerName, tSerNum, tTrapText}
	STATUS	current
	DESCRIPTION	"Protection 2. level - Earth Fault Current - alarm reset"
::= { notifications 167774546 }

tIDMTBESSGtAL2Activated	NOTIFICATION-TYPE
	OBJECTS	{tControllerName, tSerNum, tTrapText}
	STATUS	current
	DESCRIPTION	"Protection 2. level - IDMT BESS >A - alarm activated"
::= { notifications 167774548 }

tIDMTBESSGtAL2Disappeared	NOTIFICATION-TYPE
	OBJECTS	{tControllerName, tSerNum, tTrapText}
	STATUS	current
	DESCRIPTION	"Protection 2. level - IDMT BESS >A - alarm disappeared"
::= { notifications 167774549 }

tIDMTBESSGtAL2AlarmReset	NOTIFICATION-TYPE
	OBJECTS	{tControllerName, tSerNum, tTrapText}
	STATUS	current
	DESCRIPTION	"Protection 2. level - IDMT BESS >A - alarm reset"
::= { notifications 167774550 }

tIDMTEarthFaultCurrentL2Activated	NOTIFICATION-TYPE
	OBJECTS	{tControllerName, tSerNum, tTrapText}
	STATUS	current
	DESCRIPTION	"Protection 2. level - IDMT Earth Fault Current - alarm activated"
::= { notifications 167774552 }

tIDMTEarthFaultCurrentL2Disappeared	NOTIFICATION-TYPE
	OBJECTS	{tControllerName, tSerNum, tTrapText}
	STATUS	current
	DESCRIPTION	"Protection 2. level - IDMT Earth Fault Current - alarm disappeared"
::= { notifications 167774553 }

tIDMTEarthFaultCurrentL2AlarmReset	NOTIFICATION-TYPE
	OBJECTS	{tControllerName, tSerNum, tTrapText}
	STATUS	current
	DESCRIPTION	"Protection 2. level - IDMT Earth Fault Current - alarm reset"
::= { notifications 167774554 }

tBatteryUndervoltageL1Activated	NOTIFICATION-TYPE
	OBJECTS	{tControllerName, tSerNum, tTrapText}
	STATUS	current
	DESCRIPTION	"Protection 1. level - Battery Undervoltage - alarm activated"
::= { notifications 33558192 }

tBatteryUndervoltageL1Disappeared	NOTIFICATION-TYPE
	OBJECTS	{tControllerName, tSerNum, tTrapText}
	STATUS	current
	DESCRIPTION	"Protection 1. level - Battery Undervoltage - alarm disappeared"
::= { notifications 33558193 }

tBatteryUndervoltageL1AlarmReset	NOTIFICATION-TYPE
	OBJECTS	{tControllerName, tSerNum, tTrapText}
	STATUS	current
	DESCRIPTION	"Protection 1. level - Battery Undervoltage - alarm reset"
::= { notifications 33558194 }

tBatteryOvervoltageL1Activated	NOTIFICATION-TYPE
	OBJECTS	{tControllerName, tSerNum, tTrapText}
	STATUS	current
	DESCRIPTION	"Protection 1. level - Battery Overvoltage - alarm activated"
::= { notifications 33558196 }

tBatteryOvervoltageL1Disappeared	NOTIFICATION-TYPE
	OBJECTS	{tControllerName, tSerNum, tTrapText}
	STATUS	current
	DESCRIPTION	"Protection 1. level - Battery Overvoltage - alarm disappeared"
::= { notifications 33558197 }

tBatteryOvervoltageL1AlarmReset	NOTIFICATION-TYPE
	OBJECTS	{tControllerName, tSerNum, tTrapText}
	STATUS	current
	DESCRIPTION	"Protection 1. level - Battery Overvoltage - alarm reset"
::= { notifications 33558198 }

tOverrideAllSdL1Activated	NOTIFICATION-TYPE
	OBJECTS	{tControllerName, tSerNum, tTrapText}
	STATUS	current
	DESCRIPTION	"Protection 1. level - Override All Sd - alarm activated"
::= { notifications 33557128 }

tOverrideAllSdL1Disappeared	NOTIFICATION-TYPE
	OBJECTS	{tControllerName, tSerNum, tTrapText}
	STATUS	current
	DESCRIPTION	"Protection 1. level - Override All Sd - alarm disappeared"
::= { notifications 33557129 }

tOverrideAllSdL1AlarmReset	NOTIFICATION-TYPE
	OBJECTS	{tControllerName, tSerNum, tTrapText}
	STATUS	current
	DESCRIPTION	"Protection 1. level - Override All Sd - alarm reset"
::= { notifications 33557130 }

tReverseSynchroFailL1Activated	NOTIFICATION-TYPE
	OBJECTS	{tControllerName, tSerNum, tTrapText}
	STATUS	current
	DESCRIPTION	"Protection 1. level - Reverse Synchro Fail - alarm activated"
::= { notifications 33554804 }

tReverseSynchroFailL1Disappeared	NOTIFICATION-TYPE
	OBJECTS	{tControllerName, tSerNum, tTrapText}
	STATUS	current
	DESCRIPTION	"Protection 1. level - Reverse Synchro Fail - alarm disappeared"
::= { notifications 33554805 }

tReverseSynchroFailL1AlarmReset	NOTIFICATION-TYPE
	OBJECTS	{tControllerName, tSerNum, tTrapText}
	STATUS	current
	DESCRIPTION	"Protection 1. level - Reverse Synchro Fail - alarm reset"
::= { notifications 33554806 }

tSynchronizationFailL2Activated	NOTIFICATION-TYPE
	OBJECTS	{tControllerName, tSerNum, tTrapText}
	STATUS	current
	DESCRIPTION	"Protection 2. level - Synchronization Fail - alarm activated"
::= { notifications 167772536 }

tSynchronizationFailL2Disappeared	NOTIFICATION-TYPE
	OBJECTS	{tControllerName, tSerNum, tTrapText}
	STATUS	current
	DESCRIPTION	"Protection 2. level - Synchronization Fail - alarm disappeared"
::= { notifications 167772537 }

tSynchronizationFailL2AlarmReset	NOTIFICATION-TYPE
	OBJECTS	{tControllerName, tSerNum, tTrapText}
	STATUS	current
	DESCRIPTION	"Protection 2. level - Synchronization Fail - alarm reset"
::= { notifications 167772538 }

tFrequencyRegulationLimitL1Activated	NOTIFICATION-TYPE
	OBJECTS	{tControllerName, tSerNum, tTrapText}
	STATUS	current
	DESCRIPTION	"Protection 1. level - Frequency Regulation Limit - alarm activated"
::= { notifications 33555036 }

tFrequencyRegulationLimitL1Disappeared	NOTIFICATION-TYPE
	OBJECTS	{tControllerName, tSerNum, tTrapText}
	STATUS	current
	DESCRIPTION	"Protection 1. level - Frequency Regulation Limit - alarm disappeared"
::= { notifications 33555037 }

tFrequencyRegulationLimitL1AlarmReset	NOTIFICATION-TYPE
	OBJECTS	{tControllerName, tSerNum, tTrapText}
	STATUS	current
	DESCRIPTION	"Protection 1. level - Frequency Regulation Limit - alarm reset"
::= { notifications 33555038 }

tVoltageRegulationLimitL1Activated	NOTIFICATION-TYPE
	OBJECTS	{tControllerName, tSerNum, tTrapText}
	STATUS	current
	DESCRIPTION	"Protection 1. level - Voltage Regulation Limit - alarm activated"
::= { notifications 33555040 }

tVoltageRegulationLimitL1Disappeared	NOTIFICATION-TYPE
	OBJECTS	{tControllerName, tSerNum, tTrapText}
	STATUS	current
	DESCRIPTION	"Protection 1. level - Voltage Regulation Limit - alarm disappeared"
::= { notifications 33555041 }

tVoltageRegulationLimitL1AlarmReset	NOTIFICATION-TYPE
	OBJECTS	{tControllerName, tSerNum, tTrapText}
	STATUS	current
	DESCRIPTION	"Protection 1. level - Voltage Regulation Limit - alarm reset"
::= { notifications 33555042 }

tMainsVoltageDetectedL1Activated	NOTIFICATION-TYPE
	OBJECTS	{tControllerName, tSerNum, tTrapText}
	STATUS	current
	DESCRIPTION	"Protection 1. level - Mains Voltage Detected - alarm activated"
::= { notifications 33557568 }

tMainsVoltageDetectedL1Disappeared	NOTIFICATION-TYPE
	OBJECTS	{tControllerName, tSerNum, tTrapText}
	STATUS	current
	DESCRIPTION	"Protection 1. level - Mains Voltage Detected - alarm disappeared"
::= { notifications 33557569 }

tMainsVoltageDetectedL1AlarmReset	NOTIFICATION-TYPE
	OBJECTS	{tControllerName, tSerNum, tTrapText}
	STATUS	current
	DESCRIPTION	"Protection 1. level - Mains Voltage Detected - alarm reset"
::= { notifications 33557570 }

tFence1AlarmL1Activated1	NOTIFICATION-TYPE
	OBJECTS	{tControllerName, tSerNum, tTrapText}
	STATUS	current
	DESCRIPTION	"Protection 1. level - Fence 1 Alarm - alarm activated"
::= { notifications 33557676 }

tFence1AlarmL1Disappeared1	NOTIFICATION-TYPE
	OBJECTS	{tControllerName, tSerNum, tTrapText}
	STATUS	current
	DESCRIPTION	"Protection 1. level - Fence 1 Alarm - alarm disappeared"
::= { notifications 33557677 }

tFence1AlarmL1AlarmReset1	NOTIFICATION-TYPE
	OBJECTS	{tControllerName, tSerNum, tTrapText}
	STATUS	current
	DESCRIPTION	"Protection 1. level - Fence 1 Alarm - alarm reset"
::= { notifications 33557678 }

tFence1AlarmL2Activated1	NOTIFICATION-TYPE
	OBJECTS	{tControllerName, tSerNum, tTrapText}
	STATUS	current
	DESCRIPTION	"Protection 2. level - Fence 1 Alarm - alarm activated"
::= { notifications 167775404 }

tFence1AlarmL2Disappeared1	NOTIFICATION-TYPE
	OBJECTS	{tControllerName, tSerNum, tTrapText}
	STATUS	current
	DESCRIPTION	"Protection 2. level - Fence 1 Alarm - alarm disappeared"
::= { notifications 167775405 }

tFence1AlarmL2AlarmReset1	NOTIFICATION-TYPE
	OBJECTS	{tControllerName, tSerNum, tTrapText}
	STATUS	current
	DESCRIPTION	"Protection 2. level - Fence 1 Alarm - alarm reset"
::= { notifications 167775406 }

tFence1AlarmL1Activated2	NOTIFICATION-TYPE
	OBJECTS	{tControllerName, tSerNum, tTrapText}
	STATUS	current
	DESCRIPTION	"Protection 1. level - Fence 1 Alarm - alarm activated"
::= { notifications 33557680 }

tFence1AlarmL1Disappeared2	NOTIFICATION-TYPE
	OBJECTS	{tControllerName, tSerNum, tTrapText}
	STATUS	current
	DESCRIPTION	"Protection 1. level - Fence 1 Alarm - alarm disappeared"
::= { notifications 33557681 }

tFence1AlarmL1AlarmReset2	NOTIFICATION-TYPE
	OBJECTS	{tControllerName, tSerNum, tTrapText}
	STATUS	current
	DESCRIPTION	"Protection 1. level - Fence 1 Alarm - alarm reset"
::= { notifications 33557682 }

tFence1AlarmL2Activated2	NOTIFICATION-TYPE
	OBJECTS	{tControllerName, tSerNum, tTrapText}
	STATUS	current
	DESCRIPTION	"Protection 2. level - Fence 1 Alarm - alarm activated"
::= { notifications 167775408 }

tFence1AlarmL2Disappeared2	NOTIFICATION-TYPE
	OBJECTS	{tControllerName, tSerNum, tTrapText}
	STATUS	current
	DESCRIPTION	"Protection 2. level - Fence 1 Alarm - alarm disappeared"
::= { notifications 167775409 }

tFence1AlarmL2AlarmReset2	NOTIFICATION-TYPE
	OBJECTS	{tControllerName, tSerNum, tTrapText}
	STATUS	current
	DESCRIPTION	"Protection 2. level - Fence 1 Alarm - alarm reset"
::= { notifications 167775410 }

tFence2AlarmL1Activated1	NOTIFICATION-TYPE
	OBJECTS	{tControllerName, tSerNum, tTrapText}
	STATUS	current
	DESCRIPTION	"Protection 1. level - Fence 2 Alarm - alarm activated"
::= { notifications 33557684 }

tFence2AlarmL1Disappeared1	NOTIFICATION-TYPE
	OBJECTS	{tControllerName, tSerNum, tTrapText}
	STATUS	current
	DESCRIPTION	"Protection 1. level - Fence 2 Alarm - alarm disappeared"
::= { notifications 33557685 }

tFence2AlarmL1AlarmReset1	NOTIFICATION-TYPE
	OBJECTS	{tControllerName, tSerNum, tTrapText}
	STATUS	current
	DESCRIPTION	"Protection 1. level - Fence 2 Alarm - alarm reset"
::= { notifications 33557686 }

tFence2AlarmL2Activated1	NOTIFICATION-TYPE
	OBJECTS	{tControllerName, tSerNum, tTrapText}
	STATUS	current
	DESCRIPTION	"Protection 2. level - Fence 2 Alarm - alarm activated"
::= { notifications 167775412 }

tFence2AlarmL2Disappeared1	NOTIFICATION-TYPE
	OBJECTS	{tControllerName, tSerNum, tTrapText}
	STATUS	current
	DESCRIPTION	"Protection 2. level - Fence 2 Alarm - alarm disappeared"
::= { notifications 167775413 }

tFence2AlarmL2AlarmReset1	NOTIFICATION-TYPE
	OBJECTS	{tControllerName, tSerNum, tTrapText}
	STATUS	current
	DESCRIPTION	"Protection 2. level - Fence 2 Alarm - alarm reset"
::= { notifications 167775414 }

tFence2AlarmL1Activated2	NOTIFICATION-TYPE
	OBJECTS	{tControllerName, tSerNum, tTrapText}
	STATUS	current
	DESCRIPTION	"Protection 1. level - Fence 2 Alarm - alarm activated"
::= { notifications 33557688 }

tFence2AlarmL1Disappeared2	NOTIFICATION-TYPE
	OBJECTS	{tControllerName, tSerNum, tTrapText}
	STATUS	current
	DESCRIPTION	"Protection 1. level - Fence 2 Alarm - alarm disappeared"
::= { notifications 33557689 }

tFence2AlarmL1AlarmReset2	NOTIFICATION-TYPE
	OBJECTS	{tControllerName, tSerNum, tTrapText}
	STATUS	current
	DESCRIPTION	"Protection 1. level - Fence 2 Alarm - alarm reset"
::= { notifications 33557690 }

tFence2AlarmL2Activated2	NOTIFICATION-TYPE
	OBJECTS	{tControllerName, tSerNum, tTrapText}
	STATUS	current
	DESCRIPTION	"Protection 2. level - Fence 2 Alarm - alarm activated"
::= { notifications 167775416 }

tFence2AlarmL2Disappeared2	NOTIFICATION-TYPE
	OBJECTS	{tControllerName, tSerNum, tTrapText}
	STATUS	current
	DESCRIPTION	"Protection 2. level - Fence 2 Alarm - alarm disappeared"
::= { notifications 167775417 }

tFence2AlarmL2AlarmReset2	NOTIFICATION-TYPE
	OBJECTS	{tControllerName, tSerNum, tTrapText}
	STATUS	current
	DESCRIPTION	"Protection 2. level - Fence 2 Alarm - alarm reset"
::= { notifications 167775418 }

tUniversalGensetOverflowL1Activated	NOTIFICATION-TYPE
	OBJECTS	{tControllerName, tSerNum, tTrapText}
	STATUS	current
	DESCRIPTION	"Protection 1. level - Universal Genset Overflow - alarm activated"
::= { notifications 33565196 }

tUniversalGensetOverflowL1Disappeared	NOTIFICATION-TYPE
	OBJECTS	{tControllerName, tSerNum, tTrapText}
	STATUS	current
	DESCRIPTION	"Protection 1. level - Universal Genset Overflow - alarm disappeared"
::= { notifications 33565197 }

tUniversalGensetOverflowL1AlarmReset	NOTIFICATION-TYPE
	OBJECTS	{tControllerName, tSerNum, tTrapText}
	STATUS	current
	DESCRIPTION	"Protection 1. level - Universal Genset Overflow - alarm reset"
::= { notifications 33565198 }

tBusMeasErrorL2Activated	NOTIFICATION-TYPE
	OBJECTS	{tControllerName, tSerNum, tTrapText}
	STATUS	current
	DESCRIPTION	"Protection 2. level - Bus Meas Error - alarm activated"
::= { notifications 167772732 }

tBusMeasErrorL2Disappeared	NOTIFICATION-TYPE
	OBJECTS	{tControllerName, tSerNum, tTrapText}
	STATUS	current
	DESCRIPTION	"Protection 2. level - Bus Meas Error - alarm disappeared"
::= { notifications 167772733 }

tBusMeasErrorL2AlarmReset	NOTIFICATION-TYPE
	OBJECTS	{tControllerName, tSerNum, tTrapText}
	STATUS	current
	DESCRIPTION	"Protection 2. level - Bus Meas Error - alarm reset"
::= { notifications 167772734 }

tNCBFailL2Activated	NOTIFICATION-TYPE
	OBJECTS	{tControllerName, tSerNum, tTrapText}
	STATUS	current
	DESCRIPTION	"Protection 2. level - NCB Fail - alarm activated"
::= { notifications 167772752 }

tNCBFailL2Disappeared	NOTIFICATION-TYPE
	OBJECTS	{tControllerName, tSerNum, tTrapText}
	STATUS	current
	DESCRIPTION	"Protection 2. level - NCB Fail - alarm disappeared"
::= { notifications 167772753 }

tNCBFailL2AlarmReset	NOTIFICATION-TYPE
	OBJECTS	{tControllerName, tSerNum, tTrapText}
	STATUS	current
	DESCRIPTION	"Protection 2. level - NCB Fail - alarm reset"
::= { notifications 167772754 }

tUnsupportedPMSModeL1Activated	NOTIFICATION-TYPE
	OBJECTS	{tControllerName, tSerNum, tTrapText}
	STATUS	current
	DESCRIPTION	"Protection 1. level - Unsupported PMS Mode - alarm activated"
::= { notifications 33558608 }

tUnsupportedPMSModeL1Disappeared	NOTIFICATION-TYPE
	OBJECTS	{tControllerName, tSerNum, tTrapText}
	STATUS	current
	DESCRIPTION	"Protection 1. level - Unsupported PMS Mode - alarm disappeared"
::= { notifications 33558609 }

tUnsupportedPMSModeL1AlarmReset	NOTIFICATION-TYPE
	OBJECTS	{tControllerName, tSerNum, tTrapText}
	STATUS	current
	DESCRIPTION	"Protection 1. level - Unsupported PMS Mode - alarm reset"
::= { notifications 33558610 }

tWrongGCBControlModeL1Activated	NOTIFICATION-TYPE
	OBJECTS	{tControllerName, tSerNum, tTrapText}
	STATUS	current
	DESCRIPTION	"Protection 1. level - Wrong GCB Control Mode - alarm activated"
::= { notifications 33559804 }

tWrongGCBControlModeL1Disappeared	NOTIFICATION-TYPE
	OBJECTS	{tControllerName, tSerNum, tTrapText}
	STATUS	current
	DESCRIPTION	"Protection 1. level - Wrong GCB Control Mode - alarm disappeared"
::= { notifications 33559805 }

tWrongGCBControlModeL1AlarmReset	NOTIFICATION-TYPE
	OBJECTS	{tControllerName, tSerNum, tTrapText}
	STATUS	current
	DESCRIPTION	"Protection 1. level - Wrong GCB Control Mode - alarm reset"
::= { notifications 33559806 }

tTotalEmergencyStopL2Activated	NOTIFICATION-TYPE
	OBJECTS	{tControllerName, tSerNum, tTrapText}
	STATUS	current
	DESCRIPTION	"Protection 2. level - Total Emergency Stop - alarm activated"
::= { notifications 167776912 }

tTotalEmergencyStopL2Disappeared	NOTIFICATION-TYPE
	OBJECTS	{tControllerName, tSerNum, tTrapText}
	STATUS	current
	DESCRIPTION	"Protection 2. level - Total Emergency Stop - alarm disappeared"
::= { notifications 167776913 }

tTotalEmergencyStopL2AlarmReset	NOTIFICATION-TYPE
	OBJECTS	{tControllerName, tSerNum, tTrapText}
	STATUS	current
	DESCRIPTION	"Protection 2. level - Total Emergency Stop - alarm reset"
::= { notifications 167776914 }

tLoadIMPCHR2FEXPFailL1Activated	NOTIFICATION-TYPE
	OBJECTS	{tControllerName, tSerNum, tTrapText}
	STATUS	current
	DESCRIPTION	"Protection 1. level - Load IMP/EXP Fail - alarm activated"
::= { notifications 33560224 }

tLoadIMPCHR2FEXPFailL1Disappeared	NOTIFICATION-TYPE
	OBJECTS	{tControllerName, tSerNum, tTrapText}
	STATUS	current
	DESCRIPTION	"Protection 1. level - Load IMP/EXP Fail - alarm disappeared"
::= { notifications 33560225 }

tLoadIMPCHR2FEXPFailL1AlarmReset	NOTIFICATION-TYPE
	OBJECTS	{tControllerName, tSerNum, tTrapText}
	STATUS	current
	DESCRIPTION	"Protection 1. level - Load IMP/EXP Fail - alarm reset"
::= { notifications 33560226 }

tPFCHR2FQIMPCHR2FEXPFailL1Activated	NOTIFICATION-TYPE
	OBJECTS	{tControllerName, tSerNum, tTrapText}
	STATUS	current
	DESCRIPTION	"Protection 1. level - PF/Q IMP/EXP Fail - alarm activated"
::= { notifications 33558648 }

tPFCHR2FQIMPCHR2FEXPFailL1Disappeared	NOTIFICATION-TYPE
	OBJECTS	{tControllerName, tSerNum, tTrapText}
	STATUS	current
	DESCRIPTION	"Protection 1. level - PF/Q IMP/EXP Fail - alarm disappeared"
::= { notifications 33558649 }

tPFCHR2FQIMPCHR2FEXPFailL1AlarmReset	NOTIFICATION-TYPE
	OBJECTS	{tControllerName, tSerNum, tTrapText}
	STATUS	current
	DESCRIPTION	"Protection 1. level - PF/Q IMP/EXP Fail - alarm reset"
::= { notifications 33558650 }

tPFControlFailL1Activated	NOTIFICATION-TYPE
	OBJECTS	{tControllerName, tSerNum, tTrapText}
	STATUS	current
	DESCRIPTION	"Protection 1. level - PF Control Fail - alarm activated"
::= { notifications 33558644 }

tPFControlFailL1Disappeared	NOTIFICATION-TYPE
	OBJECTS	{tControllerName, tSerNum, tTrapText}
	STATUS	current
	DESCRIPTION	"Protection 1. level - PF Control Fail - alarm disappeared"
::= { notifications 33558645 }

tPFControlFailL1AlarmReset	NOTIFICATION-TYPE
	OBJECTS	{tControllerName, tSerNum, tTrapText}
	STATUS	current
	DESCRIPTION	"Protection 1. level - PF Control Fail - alarm reset"
::= { notifications 33558646 }

tQControlFailL1Activated	NOTIFICATION-TYPE
	OBJECTS	{tControllerName, tSerNum, tTrapText}
	STATUS	current
	DESCRIPTION	"Protection 1. level - Q Control Fail - alarm activated"
::= { notifications 33558628 }

tQControlFailL1Disappeared	NOTIFICATION-TYPE
	OBJECTS	{tControllerName, tSerNum, tTrapText}
	STATUS	current
	DESCRIPTION	"Protection 1. level - Q Control Fail - alarm disappeared"
::= { notifications 33558629 }

tQControlFailL1AlarmReset	NOTIFICATION-TYPE
	OBJECTS	{tControllerName, tSerNum, tTrapText}
	STATUS	current
	DESCRIPTION	"Protection 1. level - Q Control Fail - alarm reset"
::= { notifications 33558630 }

tQBroUmBrcFailL1Activated	NOTIFICATION-TYPE
	OBJECTS	{tControllerName, tSerNum, tTrapText}
	STATUS	current
	DESCRIPTION	"Protection 1. level - Q(Um) Fail - alarm activated"
::= { notifications 33558632 }

tQBroUmBrcFailL1Disappeared	NOTIFICATION-TYPE
	OBJECTS	{tControllerName, tSerNum, tTrapText}
	STATUS	current
	DESCRIPTION	"Protection 1. level - Q(Um) Fail - alarm disappeared"
::= { notifications 33558633 }

tQBroUmBrcFailL1AlarmReset	NOTIFICATION-TYPE
	OBJECTS	{tControllerName, tSerNum, tTrapText}
	STATUS	current
	DESCRIPTION	"Protection 1. level - Q(Um) Fail - alarm reset"
::= { notifications 33558634 }

tQrefCHR2FUlimFailL1Activated	NOTIFICATION-TYPE
	OBJECTS	{tControllerName, tSerNum, tTrapText}
	STATUS	current
	DESCRIPTION	"Protection 1. level - Qref/Ulim Fail - alarm activated"
::= { notifications 33558640 }

tQrefCHR2FUlimFailL1Disappeared	NOTIFICATION-TYPE
	OBJECTS	{tControllerName, tSerNum, tTrapText}
	STATUS	current
	DESCRIPTION	"Protection 1. level - Qref/Ulim Fail - alarm disappeared"
::= { notifications 33558641 }

tQrefCHR2FUlimFailL1AlarmReset	NOTIFICATION-TYPE
	OBJECTS	{tControllerName, tSerNum, tTrapText}
	STATUS	current
	DESCRIPTION	"Protection 1. level - Qref/Ulim Fail - alarm reset"
::= { notifications 33558642 }

tQBroPBrcFailL1Activated	NOTIFICATION-TYPE
	OBJECTS	{tControllerName, tSerNum, tTrapText}
	STATUS	current
	DESCRIPTION	"Protection 1. level - Q(P) Fail - alarm activated"
::= { notifications 33558636 }

tQBroPBrcFailL1Disappeared	NOTIFICATION-TYPE
	OBJECTS	{tControllerName, tSerNum, tTrapText}
	STATUS	current
	DESCRIPTION	"Protection 1. level - Q(P) Fail - alarm disappeared"
::= { notifications 33558637 }

tQBroPBrcFailL1AlarmReset	NOTIFICATION-TYPE
	OBJECTS	{tControllerName, tSerNum, tTrapText}
	STATUS	current
	DESCRIPTION	"Protection 1. level - Q(P) Fail - alarm reset"
::= { notifications 33558638 }

tPFBroPmBrcFailL1Activated	NOTIFICATION-TYPE
	OBJECTS	{tControllerName, tSerNum, tTrapText}
	STATUS	current
	DESCRIPTION	"Protection 1. level - PF(Pm) Fail - alarm activated"
::= { notifications 33558624 }

tPFBroPmBrcFailL1Disappeared	NOTIFICATION-TYPE
	OBJECTS	{tControllerName, tSerNum, tTrapText}
	STATUS	current
	DESCRIPTION	"Protection 1. level - PF(Pm) Fail - alarm disappeared"
::= { notifications 33558625 }

tPFBroPmBrcFailL1AlarmReset	NOTIFICATION-TYPE
	OBJECTS	{tControllerName, tSerNum, tTrapText}
	STATUS	current
	DESCRIPTION	"Protection 1. level - PF(Pm) Fail - alarm reset"
::= { notifications 33558626 }

tTestUPQFL1Activated	NOTIFICATION-TYPE
	OBJECTS	{tControllerName, tSerNum, tTrapText}
	STATUS	current
	DESCRIPTION	"Protection 1. level - Test UPQF - alarm activated"
::= { notifications 33556764 }

tTestUPQFL1Disappeared	NOTIFICATION-TYPE
	OBJECTS	{tControllerName, tSerNum, tTrapText}
	STATUS	current
	DESCRIPTION	"Protection 1. level - Test UPQF - alarm disappeared"
::= { notifications 33556765 }

tTestUPQFL1AlarmReset	NOTIFICATION-TYPE
	OBJECTS	{tControllerName, tSerNum, tTrapText}
	STATUS	current
	DESCRIPTION	"Protection 1. level - Test UPQF - alarm reset"
::= { notifications 33556766 }

tPForQFailL1Activated	NOTIFICATION-TYPE
	OBJECTS	{tControllerName, tSerNum, tTrapText}
	STATUS	current
	DESCRIPTION	"Protection 1. level - P For Q Fail - alarm activated"
::= { notifications 33558856 }

tPForQFailL1Disappeared	NOTIFICATION-TYPE
	OBJECTS	{tControllerName, tSerNum, tTrapText}
	STATUS	current
	DESCRIPTION	"Protection 1. level - P For Q Fail - alarm disappeared"
::= { notifications 33558857 }

tPForQFailL1AlarmReset	NOTIFICATION-TYPE
	OBJECTS	{tControllerName, tSerNum, tTrapText}
	STATUS	current
	DESCRIPTION	"Protection 1. level - P For Q Fail - alarm reset"
::= { notifications 33558858 }

tPBroUmBrcFailL1Activated	NOTIFICATION-TYPE
	OBJECTS	{tControllerName, tSerNum, tTrapText}
	STATUS	current
	DESCRIPTION	"Protection 1. level - P(Um) Fail - alarm activated"
::= { notifications 33559452 }

tPBroUmBrcFailL1Disappeared	NOTIFICATION-TYPE
	OBJECTS	{tControllerName, tSerNum, tTrapText}
	STATUS	current
	DESCRIPTION	"Protection 1. level - P(Um) Fail - alarm disappeared"
::= { notifications 33559453 }

tPBroUmBrcFailL1AlarmReset	NOTIFICATION-TYPE
	OBJECTS	{tControllerName, tSerNum, tTrapText}
	STATUS	current
	DESCRIPTION	"Protection 1. level - P(Um) Fail - alarm reset"
::= { notifications 33559454 }

tStartBlockingL1Activated	NOTIFICATION-TYPE
	OBJECTS	{tControllerName, tSerNum, tTrapText}
	STATUS	current
	DESCRIPTION	"Protection 1. level - Start blocking - alarm activated"
::= { notifications 33554656 }

tStartBlockingL1Disappeared	NOTIFICATION-TYPE
	OBJECTS	{tControllerName, tSerNum, tTrapText}
	STATUS	current
	DESCRIPTION	"Protection 1. level - Start blocking - alarm disappeared"
::= { notifications 33554657 }

tStartBlockingL1AlarmReset	NOTIFICATION-TYPE
	OBJECTS	{tControllerName, tSerNum, tTrapText}
	STATUS	current
	DESCRIPTION	"Protection 1. level - Start blocking - alarm reset"
::= { notifications 33554658 }

tDailyBatteryCyclesReachedL1Activated	NOTIFICATION-TYPE
	OBJECTS	{tControllerName, tSerNum, tTrapText}
	STATUS	current
	DESCRIPTION	"Protection 1. level - Daily Battery Cycles Reached - alarm activated"
::= { notifications 33560852 }

tDailyBatteryCyclesReachedL1Disappeared	NOTIFICATION-TYPE
	OBJECTS	{tControllerName, tSerNum, tTrapText}
	STATUS	current
	DESCRIPTION	"Protection 1. level - Daily Battery Cycles Reached - alarm disappeared"
::= { notifications 33560853 }

tDailyBatteryCyclesReachedL1AlarmReset	NOTIFICATION-TYPE
	OBJECTS	{tControllerName, tSerNum, tTrapText}
	STATUS	current
	DESCRIPTION	"Protection 1. level - Daily Battery Cycles Reached - alarm reset"
::= { notifications 33560854 }

tCANIntercontrollerEmptyL1Activated	NOTIFICATION-TYPE
	OBJECTS	{tControllerName, tSerNum, tTrapText}
	STATUS	current
	DESCRIPTION	"Protection 1. level - CAN Intercontroller Empty - alarm activated"
::= { notifications 33554616 }

tCANIntercontrollerEmptyL1Disappeared	NOTIFICATION-TYPE
	OBJECTS	{tControllerName, tSerNum, tTrapText}
	STATUS	current
	DESCRIPTION	"Protection 1. level - CAN Intercontroller Empty - alarm disappeared"
::= { notifications 33554617 }

tCANIntercontrollerEmptyL1AlarmReset	NOTIFICATION-TYPE
	OBJECTS	{tControllerName, tSerNum, tTrapText}
	STATUS	current
	DESCRIPTION	"Protection 1. level - CAN Intercontroller Empty - alarm reset"
::= { notifications 33554618 }

tresL1Activated10	NOTIFICATION-TYPE
	OBJECTS	{tControllerName, tSerNum, tTrapText}
	STATUS	current
	DESCRIPTION	"Protection 1. level - res - alarm activated"
::= { notifications 33560284 }

tresL1Disappeared10	NOTIFICATION-TYPE
	OBJECTS	{tControllerName, tSerNum, tTrapText}
	STATUS	current
	DESCRIPTION	"Protection 1. level - res - alarm disappeared"
::= { notifications 33560285 }

tresL1AlarmReset10	NOTIFICATION-TYPE
	OBJECTS	{tControllerName, tSerNum, tTrapText}
	STATUS	current
	DESCRIPTION	"Protection 1. level - res - alarm reset"
::= { notifications 33560286 }

tSWKeyModbusMasterErrorL1Activated	NOTIFICATION-TYPE
	OBJECTS	{tControllerName, tSerNum, tTrapText}
	STATUS	current
	DESCRIPTION	"Protection 1. level - SW Key Modbus Master Error - alarm activated"
::= { notifications 33559576 }

tSWKeyModbusMasterErrorL1Disappeared	NOTIFICATION-TYPE
	OBJECTS	{tControllerName, tSerNum, tTrapText}
	STATUS	current
	DESCRIPTION	"Protection 1. level - SW Key Modbus Master Error - alarm disappeared"
::= { notifications 33559577 }

tSWKeyModbusMasterErrorL1AlarmReset	NOTIFICATION-TYPE
	OBJECTS	{tControllerName, tSerNum, tTrapText}
	STATUS	current
	DESCRIPTION	"Protection 1. level - SW Key Modbus Master Error - alarm reset"
::= { notifications 33559578 }

tresL1Activated11	NOTIFICATION-TYPE
	OBJECTS	{tControllerName, tSerNum, tTrapText}
	STATUS	current
	DESCRIPTION	"Protection 1. level - res - alarm activated"
::= { notifications 33560276 }

tresL1Disappeared11	NOTIFICATION-TYPE
	OBJECTS	{tControllerName, tSerNum, tTrapText}
	STATUS	current
	DESCRIPTION	"Protection 1. level - res - alarm disappeared"
::= { notifications 33560277 }

tresL1AlarmReset11	NOTIFICATION-TYPE
	OBJECTS	{tControllerName, tSerNum, tTrapText}
	STATUS	current
	DESCRIPTION	"Protection 1. level - res - alarm reset"
::= { notifications 33560278 }

tresL1Activated12	NOTIFICATION-TYPE
	OBJECTS	{tControllerName, tSerNum, tTrapText}
	STATUS	current
	DESCRIPTION	"Protection 1. level - res - alarm activated"
::= { notifications 33560468 }

tresL1Disappeared12	NOTIFICATION-TYPE
	OBJECTS	{tControllerName, tSerNum, tTrapText}
	STATUS	current
	DESCRIPTION	"Protection 1. level - res - alarm disappeared"
::= { notifications 33560469 }

tresL1AlarmReset12	NOTIFICATION-TYPE
	OBJECTS	{tControllerName, tSerNum, tTrapText}
	STATUS	current
	DESCRIPTION	"Protection 1. level - res - alarm reset"
::= { notifications 33560470 }

tresL1Activated13	NOTIFICATION-TYPE
	OBJECTS	{tControllerName, tSerNum, tTrapText}
	STATUS	current
	DESCRIPTION	"Protection 1. level - res - alarm activated"
::= { notifications 33560676 }

tresL1Disappeared13	NOTIFICATION-TYPE
	OBJECTS	{tControllerName, tSerNum, tTrapText}
	STATUS	current
	DESCRIPTION	"Protection 1. level - res - alarm disappeared"
::= { notifications 33560677 }

tresL1AlarmReset13	NOTIFICATION-TYPE
	OBJECTS	{tControllerName, tSerNum, tTrapText}
	STATUS	current
	DESCRIPTION	"Protection 1. level - res - alarm reset"
::= { notifications 33560678 }

tresL1Activated14	NOTIFICATION-TYPE
	OBJECTS	{tControllerName, tSerNum, tTrapText}
	STATUS	current
	DESCRIPTION	"Protection 1. level - res - alarm activated"
::= { notifications 33560844 }

tresL1Disappeared14	NOTIFICATION-TYPE
	OBJECTS	{tControllerName, tSerNum, tTrapText}
	STATUS	current
	DESCRIPTION	"Protection 1. level - res - alarm disappeared"
::= { notifications 33560845 }

tresL1AlarmReset14	NOTIFICATION-TYPE
	OBJECTS	{tControllerName, tSerNum, tTrapText}
	STATUS	current
	DESCRIPTION	"Protection 1. level - res - alarm reset"
::= { notifications 33560846 }

tresL1Activated15	NOTIFICATION-TYPE
	OBJECTS	{tControllerName, tSerNum, tTrapText}
	STATUS	current
	DESCRIPTION	"Protection 1. level - res - alarm activated"
::= { notifications 33560888 }

tresL1Disappeared15	NOTIFICATION-TYPE
	OBJECTS	{tControllerName, tSerNum, tTrapText}
	STATUS	current
	DESCRIPTION	"Protection 1. level - res - alarm disappeared"
::= { notifications 33560889 }

tresL1AlarmReset15	NOTIFICATION-TYPE
	OBJECTS	{tControllerName, tSerNum, tTrapText}
	STATUS	current
	DESCRIPTION	"Protection 1. level - res - alarm reset"
::= { notifications 33560890 }

tresL1Activated16	NOTIFICATION-TYPE
	OBJECTS	{tControllerName, tSerNum, tTrapText}
	STATUS	current
	DESCRIPTION	"Protection 1. level - res - alarm activated"
::= { notifications 33560932 }

tresL1Disappeared16	NOTIFICATION-TYPE
	OBJECTS	{tControllerName, tSerNum, tTrapText}
	STATUS	current
	DESCRIPTION	"Protection 1. level - res - alarm disappeared"
::= { notifications 33560933 }

tresL1AlarmReset16	NOTIFICATION-TYPE
	OBJECTS	{tControllerName, tSerNum, tTrapText}
	STATUS	current
	DESCRIPTION	"Protection 1. level - res - alarm reset"
::= { notifications 33560934 }

tresL1Activated17	NOTIFICATION-TYPE
	OBJECTS	{tControllerName, tSerNum, tTrapText}
	STATUS	current
	DESCRIPTION	"Protection 1. level - res - alarm activated"
::= { notifications 33560940 }

tresL1Disappeared17	NOTIFICATION-TYPE
	OBJECTS	{tControllerName, tSerNum, tTrapText}
	STATUS	current
	DESCRIPTION	"Protection 1. level - res - alarm disappeared"
::= { notifications 33560941 }

tresL1AlarmReset17	NOTIFICATION-TYPE
	OBJECTS	{tControllerName, tSerNum, tTrapText}
	STATUS	current
	DESCRIPTION	"Protection 1. level - res - alarm reset"
::= { notifications 33560942 }

tresL1Activated18	NOTIFICATION-TYPE
	OBJECTS	{tControllerName, tSerNum, tTrapText}
	STATUS	current
	DESCRIPTION	"Protection 1. level - res - alarm activated"
::= { notifications 33560948 }

tresL1Disappeared18	NOTIFICATION-TYPE
	OBJECTS	{tControllerName, tSerNum, tTrapText}
	STATUS	current
	DESCRIPTION	"Protection 1. level - res - alarm disappeared"
::= { notifications 33560949 }

tresL1AlarmReset18	NOTIFICATION-TYPE
	OBJECTS	{tControllerName, tSerNum, tTrapText}
	STATUS	current
	DESCRIPTION	"Protection 1. level - res - alarm reset"
::= { notifications 33560950 }

tresL1Activated19	NOTIFICATION-TYPE
	OBJECTS	{tControllerName, tSerNum, tTrapText}
	STATUS	current
	DESCRIPTION	"Protection 1. level - res - alarm activated"
::= { notifications 33561020 }

tresL1Disappeared19	NOTIFICATION-TYPE
	OBJECTS	{tControllerName, tSerNum, tTrapText}
	STATUS	current
	DESCRIPTION	"Protection 1. level - res - alarm disappeared"
::= { notifications 33561021 }

tresL1AlarmReset19	NOTIFICATION-TYPE
	OBJECTS	{tControllerName, tSerNum, tTrapText}
	STATUS	current
	DESCRIPTION	"Protection 1. level - res - alarm reset"
::= { notifications 33561022 }

tSWKeyCANControllersErrorL1Activated	NOTIFICATION-TYPE
	OBJECTS	{tControllerName, tSerNum, tTrapText}
	STATUS	current
	DESCRIPTION	"Protection 1. level - SW Key CAN Controllers Error - alarm activated"
::= { notifications 33561024 }

tSWKeyCANControllersErrorL1Disappeared	NOTIFICATION-TYPE
	OBJECTS	{tControllerName, tSerNum, tTrapText}
	STATUS	current
	DESCRIPTION	"Protection 1. level - SW Key CAN Controllers Error - alarm disappeared"
::= { notifications 33561025 }

tSWKeyCANControllersErrorL1AlarmReset	NOTIFICATION-TYPE
	OBJECTS	{tControllerName, tSerNum, tTrapText}
	STATUS	current
	DESCRIPTION	"Protection 1. level - SW Key CAN Controllers Error - alarm reset"
::= { notifications 33561026 }

tresL1Activated20	NOTIFICATION-TYPE
	OBJECTS	{tControllerName, tSerNum, tTrapText}
	STATUS	current
	DESCRIPTION	"Protection 1. level - res - alarm activated"
::= { notifications 33561056 }

tresL1Disappeared20	NOTIFICATION-TYPE
	OBJECTS	{tControllerName, tSerNum, tTrapText}
	STATUS	current
	DESCRIPTION	"Protection 1. level - res - alarm disappeared"
::= { notifications 33561057 }

tresL1AlarmReset20	NOTIFICATION-TYPE
	OBJECTS	{tControllerName, tSerNum, tTrapText}
	STATUS	current
	DESCRIPTION	"Protection 1. level - res - alarm reset"
::= { notifications 33561058 }

tresL1Activated21	NOTIFICATION-TYPE
	OBJECTS	{tControllerName, tSerNum, tTrapText}
	STATUS	current
	DESCRIPTION	"Protection 1. level - res - alarm activated"
::= { notifications 33563872 }

tresL1Disappeared21	NOTIFICATION-TYPE
	OBJECTS	{tControllerName, tSerNum, tTrapText}
	STATUS	current
	DESCRIPTION	"Protection 1. level - res - alarm disappeared"
::= { notifications 33563873 }

tresL1AlarmReset21	NOTIFICATION-TYPE
	OBJECTS	{tControllerName, tSerNum, tTrapText}
	STATUS	current
	DESCRIPTION	"Protection 1. level - res - alarm reset"
::= { notifications 33563874 }

tUniGenSWKeyMissingL1Activated	NOTIFICATION-TYPE
	OBJECTS	{tControllerName, tSerNum, tTrapText}
	STATUS	current
	DESCRIPTION	"Protection 1. level - Uni Gen SW Key Missing - alarm activated"
::= { notifications 33563876 }

tUniGenSWKeyMissingL1Disappeared	NOTIFICATION-TYPE
	OBJECTS	{tControllerName, tSerNum, tTrapText}
	STATUS	current
	DESCRIPTION	"Protection 1. level - Uni Gen SW Key Missing - alarm disappeared"
::= { notifications 33563877 }

tUniGenSWKeyMissingL1AlarmReset	NOTIFICATION-TYPE
	OBJECTS	{tControllerName, tSerNum, tTrapText}
	STATUS	current
	DESCRIPTION	"Protection 1. level - Uni Gen SW Key Missing - alarm reset"
::= { notifications 33563878 }

tPVNotOperableL2Activated	NOTIFICATION-TYPE
	OBJECTS	{tControllerName, tSerNum, tTrapText}
	STATUS	current
	DESCRIPTION	"Protection 2. level - PV Not Operable - alarm activated"
::= { notifications 167778528 }

tPVNotOperableL2Disappeared	NOTIFICATION-TYPE
	OBJECTS	{tControllerName, tSerNum, tTrapText}
	STATUS	current
	DESCRIPTION	"Protection 2. level - PV Not Operable - alarm disappeared"
::= { notifications 167778529 }

tPVNotOperableL2AlarmReset	NOTIFICATION-TYPE
	OBJECTS	{tControllerName, tSerNum, tTrapText}
	STATUS	current
	DESCRIPTION	"Protection 2. level - PV Not Operable - alarm reset"
::= { notifications 167778530 }

tPVAntiIslandingL2Activated	NOTIFICATION-TYPE
	OBJECTS	{tControllerName, tSerNum, tTrapText}
	STATUS	current
	DESCRIPTION	"Protection 2. level - PV Anti Islanding - alarm activated"
::= { notifications 167778532 }

tPVAntiIslandingL2Disappeared	NOTIFICATION-TYPE
	OBJECTS	{tControllerName, tSerNum, tTrapText}
	STATUS	current
	DESCRIPTION	"Protection 2. level - PV Anti Islanding - alarm disappeared"
::= { notifications 167778533 }

tPVAntiIslandingL2AlarmReset	NOTIFICATION-TYPE
	OBJECTS	{tControllerName, tSerNum, tTrapText}
	STATUS	current
	DESCRIPTION	"Protection 2. level - PV Anti Islanding - alarm reset"
::= { notifications 167778534 }

tSOCLowAlarmL1Activated	NOTIFICATION-TYPE
	OBJECTS	{tControllerName, tSerNum, tTrapText}
	STATUS	current
	DESCRIPTION	"Protection 1. level - SOC Low Alarm - alarm activated"
::= { notifications 33560808 }

tSOCLowAlarmL1Disappeared	NOTIFICATION-TYPE
	OBJECTS	{tControllerName, tSerNum, tTrapText}
	STATUS	current
	DESCRIPTION	"Protection 1. level - SOC Low Alarm - alarm disappeared"
::= { notifications 33560809 }

tSOCLowAlarmL1AlarmReset	NOTIFICATION-TYPE
	OBJECTS	{tControllerName, tSerNum, tTrapText}
	STATUS	current
	DESCRIPTION	"Protection 1. level - SOC Low Alarm - alarm reset"
::= { notifications 33560810 }

tSOCHighAlarmL1Activated	NOTIFICATION-TYPE
	OBJECTS	{tControllerName, tSerNum, tTrapText}
	STATUS	current
	DESCRIPTION	"Protection 1. level - SOC High Alarm - alarm activated"
::= { notifications 33560812 }

tSOCHighAlarmL1Disappeared	NOTIFICATION-TYPE
	OBJECTS	{tControllerName, tSerNum, tTrapText}
	STATUS	current
	DESCRIPTION	"Protection 1. level - SOC High Alarm - alarm disappeared"
::= { notifications 33560813 }

tSOCHighAlarmL1AlarmReset	NOTIFICATION-TYPE
	OBJECTS	{tControllerName, tSerNum, tTrapText}
	STATUS	current
	DESCRIPTION	"Protection 1. level - SOC High Alarm - alarm reset"
::= { notifications 33560814 }

tSOCCriticalLowL2Activated	NOTIFICATION-TYPE
	OBJECTS	{tControllerName, tSerNum, tTrapText}
	STATUS	current
	DESCRIPTION	"Protection 2. level - SOC Critical Low - alarm activated"
::= { notifications 167778544 }

tSOCCriticalLowL2Disappeared	NOTIFICATION-TYPE
	OBJECTS	{tControllerName, tSerNum, tTrapText}
	STATUS	current
	DESCRIPTION	"Protection 2. level - SOC Critical Low - alarm disappeared"
::= { notifications 167778545 }

tSOCCriticalLowL2AlarmReset	NOTIFICATION-TYPE
	OBJECTS	{tControllerName, tSerNum, tTrapText}
	STATUS	current
	DESCRIPTION	"Protection 2. level - SOC Critical Low - alarm reset"
::= { notifications 167778546 }

tSOCCriticalHighL2Activated	NOTIFICATION-TYPE
	OBJECTS	{tControllerName, tSerNum, tTrapText}
	STATUS	current
	DESCRIPTION	"Protection 2. level - SOC Critical High - alarm activated"
::= { notifications 167778548 }

tSOCCriticalHighL2Disappeared	NOTIFICATION-TYPE
	OBJECTS	{tControllerName, tSerNum, tTrapText}
	STATUS	current
	DESCRIPTION	"Protection 2. level - SOC Critical High - alarm disappeared"
::= { notifications 167778549 }

tSOCCriticalHighL2AlarmReset	NOTIFICATION-TYPE
	OBJECTS	{tControllerName, tSerNum, tTrapText}
	STATUS	current
	DESCRIPTION	"Protection 2. level - SOC Critical High - alarm reset"
::= { notifications 167778550 }

tBESSSOCNotConfiguredL2Activated	NOTIFICATION-TYPE
	OBJECTS	{tControllerName, tSerNum, tTrapText}
	STATUS	current
	DESCRIPTION	"Protection 2. level - BESS SOC Not Configured - alarm activated"
::= { notifications 167778768 }

tBESSSOCNotConfiguredL2Disappeared	NOTIFICATION-TYPE
	OBJECTS	{tControllerName, tSerNum, tTrapText}
	STATUS	current
	DESCRIPTION	"Protection 2. level - BESS SOC Not Configured - alarm disappeared"
::= { notifications 167778769 }

tBESSSOCNotConfiguredL2AlarmReset	NOTIFICATION-TYPE
	OBJECTS	{tControllerName, tSerNum, tTrapText}
	STATUS	current
	DESCRIPTION	"Protection 2. level - BESS SOC Not Configured - alarm reset"
::= { notifications 167778770 }

tBESSSOCNotAvailableL2Activated	NOTIFICATION-TYPE
	OBJECTS	{tControllerName, tSerNum, tTrapText}
	STATUS	current
	DESCRIPTION	"Protection 2. level - BESS SOC Not Available - alarm activated"
::= { notifications 167778772 }

tBESSSOCNotAvailableL2Disappeared	NOTIFICATION-TYPE
	OBJECTS	{tControllerName, tSerNum, tTrapText}
	STATUS	current
	DESCRIPTION	"Protection 2. level - BESS SOC Not Available - alarm disappeared"
::= { notifications 167778773 }

tBESSSOCNotAvailableL2AlarmReset	NOTIFICATION-TYPE
	OBJECTS	{tControllerName, tSerNum, tTrapText}
	STATUS	current
	DESCRIPTION	"Protection 2. level - BESS SOC Not Available - alarm reset"
::= { notifications 167778774 }

tDCCircuitCloseFailL2Activated	NOTIFICATION-TYPE
	OBJECTS	{tControllerName, tSerNum, tTrapText}
	STATUS	current
	DESCRIPTION	"Protection 2. level - DC Circuit Close Fail - alarm activated"
::= { notifications 167778780 }

tDCCircuitCloseFailL2Disappeared	NOTIFICATION-TYPE
	OBJECTS	{tControllerName, tSerNum, tTrapText}
	STATUS	current
	DESCRIPTION	"Protection 2. level - DC Circuit Close Fail - alarm disappeared"
::= { notifications 167778781 }

tDCCircuitCloseFailL2AlarmReset	NOTIFICATION-TYPE
	OBJECTS	{tControllerName, tSerNum, tTrapText}
	STATUS	current
	DESCRIPTION	"Protection 2. level - DC Circuit Close Fail - alarm reset"
::= { notifications 167778782 }

tBCBClosingIsBlockedL1Activated	NOTIFICATION-TYPE
	OBJECTS	{tControllerName, tSerNum, tTrapText}
	STATUS	current
	DESCRIPTION	"Protection 1. level - BCB Closing Is Blocked - alarm activated"
::= { notifications 33563788 }

tBCBClosingIsBlockedL1Disappeared	NOTIFICATION-TYPE
	OBJECTS	{tControllerName, tSerNum, tTrapText}
	STATUS	current
	DESCRIPTION	"Protection 1. level - BCB Closing Is Blocked - alarm disappeared"
::= { notifications 33563789 }

tBCBClosingIsBlockedL1AlarmReset	NOTIFICATION-TYPE
	OBJECTS	{tControllerName, tSerNum, tTrapText}
	STATUS	current
	DESCRIPTION	"Protection 1. level - BCB Closing Is Blocked - alarm reset"
::= { notifications 33563790 }

tEMBroABrcAMessageLost	NOTIFICATION-TYPE
	OBJECTS	{tControllerName, tSerNum, tTrapText}
	STATUS	current
	DESCRIPTION	"Event: EM(A) - a message lost"
::= { notifications 1073741896 }

tEMBroBBrcAMessageLost	NOTIFICATION-TYPE
	OBJECTS	{tControllerName, tSerNum, tTrapText}
	STATUS	current
	DESCRIPTION	"Event: EM(B) - a message lost"
::= { notifications 1073741897 }

tFaultReset	NOTIFICATION-TYPE
	OBJECTS	{tControllerName, tSerNum, tTrapText}
	STATUS	current
	DESCRIPTION	"Event: Fault reset"
::= { notifications 1073741848 }

tEventEMail1OK	NOTIFICATION-TYPE
	OBJECTS	{tControllerName, tSerNum, tTrapText}
	STATUS	current
	DESCRIPTION	"Event: Event e-mail 1 OK"
::= { notifications 1073741849 }

tEventEMail2OK	NOTIFICATION-TYPE
	OBJECTS	{tControllerName, tSerNum, tTrapText}
	STATUS	current
	DESCRIPTION	"Event: Event e-mail 2 OK"
::= { notifications 1073741850 }

tEventEMail3OK	NOTIFICATION-TYPE
	OBJECTS	{tControllerName, tSerNum, tTrapText}
	STATUS	current
	DESCRIPTION	"Event: Event e-mail 3 OK"
::= { notifications 1073741851 }

tEventEMail4OK	NOTIFICATION-TYPE
	OBJECTS	{tControllerName, tSerNum, tTrapText}
	STATUS	current
	DESCRIPTION	"Event: Event e-mail 4 OK"
::= { notifications 1073741852 }

tEventSMS1OK	NOTIFICATION-TYPE
	OBJECTS	{tControllerName, tSerNum, tTrapText}
	STATUS	current
	DESCRIPTION	"Event: Event SMS 1 OK"
::= { notifications 1073741853 }

tEventSMS2OK	NOTIFICATION-TYPE
	OBJECTS	{tControllerName, tSerNum, tTrapText}
	STATUS	current
	DESCRIPTION	"Event: Event SMS 2 OK"
::= { notifications 1073741854 }

tEventSMS3OK	NOTIFICATION-TYPE
	OBJECTS	{tControllerName, tSerNum, tTrapText}
	STATUS	current
	DESCRIPTION	"Event: Event SMS 3 OK"
::= { notifications 1073741855 }

tEventSMS4OK	NOTIFICATION-TYPE
	OBJECTS	{tControllerName, tSerNum, tTrapText}
	STATUS	current
	DESCRIPTION	"Event: Event SMS 4 OK"
::= { notifications 1073741856 }

tAlarmEMail1OK	NOTIFICATION-TYPE
	OBJECTS	{tControllerName, tSerNum, tTrapText}
	STATUS	current
	DESCRIPTION	"Event: Alarm e-mail 1 OK"
::= { notifications 1073742121 }

tAlarmEMail2OK	NOTIFICATION-TYPE
	OBJECTS	{tControllerName, tSerNum, tTrapText}
	STATUS	current
	DESCRIPTION	"Event: Alarm e-mail 2 OK"
::= { notifications 1073742122 }

tAlarmEMail3OK	NOTIFICATION-TYPE
	OBJECTS	{tControllerName, tSerNum, tTrapText}
	STATUS	current
	DESCRIPTION	"Event: Alarm e-mail 3 OK"
::= { notifications 1073742125 }

tAlarmEMail4OK	NOTIFICATION-TYPE
	OBJECTS	{tControllerName, tSerNum, tTrapText}
	STATUS	current
	DESCRIPTION	"Event: Alarm e-mail 4 OK"
::= { notifications 1073742126 }

tAlarmSMS1OK	NOTIFICATION-TYPE
	OBJECTS	{tControllerName, tSerNum, tTrapText}
	STATUS	current
	DESCRIPTION	"Event: Alarm SMS 1 OK"
::= { notifications 1073742127 }

tAlarmSMS2OK	NOTIFICATION-TYPE
	OBJECTS	{tControllerName, tSerNum, tTrapText}
	STATUS	current
	DESCRIPTION	"Event: Alarm SMS 2 OK"
::= { notifications 1073742128 }

tAlarmSMS3OK	NOTIFICATION-TYPE
	OBJECTS	{tControllerName, tSerNum, tTrapText}
	STATUS	current
	DESCRIPTION	"Event: Alarm SMS 3 OK"
::= { notifications 1073742129 }

tAlarmSMS4OK	NOTIFICATION-TYPE
	OBJECTS	{tControllerName, tSerNum, tTrapText}
	STATUS	current
	DESCRIPTION	"Event: Alarm SMS 4 OK"
::= { notifications 1073742130 }

tSNMPTRAP1OK	NOTIFICATION-TYPE
	OBJECTS	{tControllerName, tSerNum, tTrapText}
	STATUS	current
	DESCRIPTION	"Event: SNMP TRAP 1 OK"
::= { notifications 1073742131 }

tSNMPTRAP2OK	NOTIFICATION-TYPE
	OBJECTS	{tControllerName, tSerNum, tTrapText}
	STATUS	current
	DESCRIPTION	"Event: SNMP TRAP 2 OK"
::= { notifications 1073742132 }

tEventEMail1Fail	NOTIFICATION-TYPE
	OBJECTS	{tControllerName, tSerNum, tTrapText}
	STATUS	current
	DESCRIPTION	"Event: Event e-mail 1 Fail"
::= { notifications 1073741857 }

tEventEMail2Fail	NOTIFICATION-TYPE
	OBJECTS	{tControllerName, tSerNum, tTrapText}
	STATUS	current
	DESCRIPTION	"Event: Event e-mail 2 Fail"
::= { notifications 1073741858 }

tEventEMail3Fail	NOTIFICATION-TYPE
	OBJECTS	{tControllerName, tSerNum, tTrapText}
	STATUS	current
	DESCRIPTION	"Event: Event e-mail 3 Fail"
::= { notifications 1073741859 }

tEventEMail4Fail	NOTIFICATION-TYPE
	OBJECTS	{tControllerName, tSerNum, tTrapText}
	STATUS	current
	DESCRIPTION	"Event: Event e-mail 4 Fail"
::= { notifications 1073741860 }

tEventSMS1Fail	NOTIFICATION-TYPE
	OBJECTS	{tControllerName, tSerNum, tTrapText}
	STATUS	current
	DESCRIPTION	"Event: Event SMS 1 Fail"
::= { notifications 1073741861 }

tEventSMS2Fail	NOTIFICATION-TYPE
	OBJECTS	{tControllerName, tSerNum, tTrapText}
	STATUS	current
	DESCRIPTION	"Event: Event SMS 2 Fail"
::= { notifications 1073741862 }

tEventSMS3Fail	NOTIFICATION-TYPE
	OBJECTS	{tControllerName, tSerNum, tTrapText}
	STATUS	current
	DESCRIPTION	"Event: Event SMS 3 Fail"
::= { notifications 1073741863 }

tEventSMS4Fail	NOTIFICATION-TYPE
	OBJECTS	{tControllerName, tSerNum, tTrapText}
	STATUS	current
	DESCRIPTION	"Event: Event SMS 4 Fail"
::= { notifications 1073741864 }

tAlarmEMail1Fail	NOTIFICATION-TYPE
	OBJECTS	{tControllerName, tSerNum, tTrapText}
	STATUS	current
	DESCRIPTION	"Event: Alarm e-mail 1 Fail"
::= { notifications 1073742123 }

tAlarmEMail2Fail	NOTIFICATION-TYPE
	OBJECTS	{tControllerName, tSerNum, tTrapText}
	STATUS	current
	DESCRIPTION	"Event: Alarm e-mail 2 Fail"
::= { notifications 1073742124 }

tAlarmEMail3Fail	NOTIFICATION-TYPE
	OBJECTS	{tControllerName, tSerNum, tTrapText}
	STATUS	current
	DESCRIPTION	"Event: Alarm e-mail 3 Fail"
::= { notifications 1073742133 }

tAlarmEMail4Fail	NOTIFICATION-TYPE
	OBJECTS	{tControllerName, tSerNum, tTrapText}
	STATUS	current
	DESCRIPTION	"Event: Alarm e-mail 4 Fail"
::= { notifications 1073742134 }

tAlarmSMS1Fail	NOTIFICATION-TYPE
	OBJECTS	{tControllerName, tSerNum, tTrapText}
	STATUS	current
	DESCRIPTION	"Event: Alarm SMS 1 Fail"
::= { notifications 1073742135 }

tAlarmSMS2Fail	NOTIFICATION-TYPE
	OBJECTS	{tControllerName, tSerNum, tTrapText}
	STATUS	current
	DESCRIPTION	"Event: Alarm SMS 2 Fail"
::= { notifications 1073742136 }

tAlarmSMS3Fail	NOTIFICATION-TYPE
	OBJECTS	{tControllerName, tSerNum, tTrapText}
	STATUS	current
	DESCRIPTION	"Event: Alarm SMS 3 Fail"
::= { notifications 1073742137 }

tAlarmSMS4Fail	NOTIFICATION-TYPE
	OBJECTS	{tControllerName, tSerNum, tTrapText}
	STATUS	current
	DESCRIPTION	"Event: Alarm SMS 4 Fail"
::= { notifications 1073742138 }

tSNMPTRAP1Fail	NOTIFICATION-TYPE
	OBJECTS	{tControllerName, tSerNum, tTrapText}
	STATUS	current
	DESCRIPTION	"Event: SNMP TRAP 1 Fail"
::= { notifications 1073742139 }

tSNMPTRAP2Fail	NOTIFICATION-TYPE
	OBJECTS	{tControllerName, tSerNum, tTrapText}
	STATUS	current
	DESCRIPTION	"Event: SNMP TRAP 2 Fail"
::= { notifications 1073742140 }

tSwitchedOn	NOTIFICATION-TYPE
	OBJECTS	{tControllerName, tSerNum, tTrapText}
	STATUS	current
	DESCRIPTION	"Event: Switched On"
::= { notifications 1073741825 }

tWatchdog	NOTIFICATION-TYPE
	OBJECTS	{tControllerName, tSerNum, tTrapText}
	STATUS	current
	DESCRIPTION	"Event: Watchdog"
::= { notifications 1073741826 }

tSystem	NOTIFICATION-TYPE
	OBJECTS	{tControllerName, tSerNum, tTrapText}
	STATUS	current
	DESCRIPTION	"Event: System"
::= { notifications 1073741865 }

tSystemLog	NOTIFICATION-TYPE
	OBJECTS	{tControllerName, tSerNum, tTrapText}
	STATUS	current
	DESCRIPTION	"Event: System Log"
::= { notifications 1073741866 }

tWrongConfig	NOTIFICATION-TYPE
	OBJECTS	{tControllerName, tSerNum, tTrapText}
	STATUS	current
	DESCRIPTION	"Event: Wrong config"
::= { notifications 1073741867 }

tSetpointChange	NOTIFICATION-TYPE
	OBJECTS	{tControllerName, tSerNum, tTrapText}
	STATUS	current
	DESCRIPTION	"Event: SetpointChange"
::= { notifications 1073741868 }

tPasswordSet	NOTIFICATION-TYPE
	OBJECTS	{tControllerName, tSerNum, tTrapText}
	STATUS	current
	DESCRIPTION	"Event: Password set"
::= { notifications 1073741869 }

tPasswordChng	NOTIFICATION-TYPE
	OBJECTS	{tControllerName, tSerNum, tTrapText}
	STATUS	current
	DESCRIPTION	"Event: Password chng"
::= { notifications 1073741870 }

tAccessCodeSet	NOTIFICATION-TYPE
	OBJECTS	{tControllerName, tSerNum, tTrapText}
	STATUS	current
	DESCRIPTION	"Event: AccessCodeSet"
::= { notifications 1073741871 }

tAccessCodeChng	NOTIFICATION-TYPE
	OBJECTS	{tControllerName, tSerNum, tTrapText}
	STATUS	current
	DESCRIPTION	"Event: AccessCodeChng"
::= { notifications 1073741872 }

tTerminal	NOTIFICATION-TYPE
	OBJECTS	{tControllerName, tSerNum, tTrapText}
	STATUS	current
	DESCRIPTION	"Event: Terminal"
::= { notifications 1073741874 }

tForcedValue	NOTIFICATION-TYPE
	OBJECTS	{tControllerName, tSerNum, tTrapText}
	STATUS	current
	DESCRIPTION	"Event: Forced Value"
::= { notifications 1073741877 }

tTimeModeChange	NOTIFICATION-TYPE
	OBJECTS	{tControllerName, tSerNum, tTrapText}
	STATUS	current
	DESCRIPTION	"Event: TimeModeChange"
::= { notifications 1073741878 }

tGroupsLinked	NOTIFICATION-TYPE
	OBJECTS	{tControllerName, tSerNum, tTrapText}
	STATUS	current
	DESCRIPTION	"Event: Groups Linked"
::= { notifications 1073741879 }

tGroupsUnlinked	NOTIFICATION-TYPE
	OBJECTS	{tControllerName, tSerNum, tTrapText}
	STATUS	current
	DESCRIPTION	"Event: Groups Unlinked"
::= { notifications 1073741880 }

tProgrammingRequest	NOTIFICATION-TYPE
	OBJECTS	{tControllerName, tSerNum, tTrapText}
	STATUS	current
	DESCRIPTION	"Event: Programming Request"
::= { notifications 1073741882 }

tProgrammingNotFinished	NOTIFICATION-TYPE
	OBJECTS	{tControllerName, tSerNum, tTrapText}
	STATUS	current
	DESCRIPTION	"Event: Programming not finished"
::= { notifications 1073741883 }

tProgrammingResult	NOTIFICATION-TYPE
	OBJECTS	{tControllerName, tSerNum, tTrapText}
	STATUS	current
	DESCRIPTION	"Event: Programming result"
::= { notifications 1073741884 }

tUnknownECUDiag	NOTIFICATION-TYPE
	OBJECTS	{tControllerName, tSerNum, tTrapText}
	STATUS	current
	DESCRIPTION	"Event: Unknown ECU diag"
::= { notifications 1073741885 }

tTerminalDiag	NOTIFICATION-TYPE
	OBJECTS	{tControllerName, tSerNum, tTrapText}
	STATUS	current
	DESCRIPTION	"Event: Terminal Diag"
::= { notifications 1073742426 }

tTimeStamp	NOTIFICATION-TYPE
	OBJECTS	{tControllerName, tSerNum, tTrapText}
	STATUS	current
	DESCRIPTION	"Event: Time Stamp"
::= { notifications 1073741985 }

tLVRTSevere	NOTIFICATION-TYPE
	OBJECTS	{tControllerName, tSerNum, tTrapText}
	STATUS	current
	DESCRIPTION	"Event: LVRT Severe"
::= { notifications 1073742506 }

tMaintenance1	NOTIFICATION-TYPE
	OBJECTS	{tControllerName, tSerNum, tTrapText}
	STATUS	current
	DESCRIPTION	"Event: Maintenance 1"
::= { notifications 1073742029 }

tMaintenance2	NOTIFICATION-TYPE
	OBJECTS	{tControllerName, tSerNum, tTrapText}
	STATUS	current
	DESCRIPTION	"Event: Maintenance 2"
::= { notifications 1073742030 }

tMaintenance3	NOTIFICATION-TYPE
	OBJECTS	{tControllerName, tSerNum, tTrapText}
	STATUS	current
	DESCRIPTION	"Event: Maintenance 3"
::= { notifications 1073742031 }

tVectorShift	NOTIFICATION-TYPE
	OBJECTS	{tControllerName, tSerNum, tTrapText}
	STATUS	current
	DESCRIPTION	"Event: Vector Shift"
::= { notifications 1073742215 }

tROCOF	NOTIFICATION-TYPE
	OBJECTS	{tControllerName, tSerNum, tTrapText}
	STATUS	current
	DESCRIPTION	"Event: ROCOF"
::= { notifications 1073742216 }

tReverseSynchroFail	NOTIFICATION-TYPE
	OBJECTS	{tControllerName, tSerNum, tTrapText}
	STATUS	current
	DESCRIPTION	"Event: Reverse synchro Fail"
::= { notifications 1073742217 }

tSynchronisationFail	NOTIFICATION-TYPE
	OBJECTS	{tControllerName, tSerNum, tTrapText}
	STATUS	current
	DESCRIPTION	"Event: Synchronisation Fail"
::= { notifications 1073742218 }

tMainsFail	NOTIFICATION-TYPE
	OBJECTS	{tControllerName, tSerNum, tTrapText}
	STATUS	current
	DESCRIPTION	"Event: Mains Fail"
::= { notifications 1073742057 }

tMainsReturned	NOTIFICATION-TYPE
	OBJECTS	{tControllerName, tSerNum, tTrapText}
	STATUS	current
	DESCRIPTION	"Event: Mains Returned"
::= { notifications 1073742058 }

tLoadOnMains	NOTIFICATION-TYPE
	OBJECTS	{tControllerName, tSerNum, tTrapText}
	STATUS	current
	DESCRIPTION	"Event: Load on Mains"
::= { notifications 1073742059 }

tLoadOnBESS	NOTIFICATION-TYPE
	OBJECTS	{tControllerName, tSerNum, tTrapText}
	STATUS	current
	DESCRIPTION	"Event: Load on BESS"
::= { notifications 1073742060 }

tPeakStart	NOTIFICATION-TYPE
	OBJECTS	{tControllerName, tSerNum, tTrapText}
	STATUS	current
	DESCRIPTION	"Event: Peak Start"
::= { notifications 1073742069 }

tPMSStart	NOTIFICATION-TYPE
	OBJECTS	{tControllerName, tSerNum, tTrapText}
	STATUS	current
	DESCRIPTION	"Event: PMS Start"
::= { notifications 1073742070 }

tModbusRemoteStart	NOTIFICATION-TYPE
	OBJECTS	{tControllerName, tSerNum, tTrapText}
	STATUS	current
	DESCRIPTION	"Event: Modbus Remote Start"
::= { notifications 1073742717 }

tRemoteStart	NOTIFICATION-TYPE
	OBJECTS	{tControllerName, tSerNum, tTrapText}
	STATUS	current
	DESCRIPTION	"Event: Remote Start"
::= { notifications 1073742071 }

tAMFStart	NOTIFICATION-TYPE
	OBJECTS	{tControllerName, tSerNum, tTrapText}
	STATUS	current
	DESCRIPTION	"Event: AMF Start"
::= { notifications 1073742072 }

tManualStart	NOTIFICATION-TYPE
	OBJECTS	{tControllerName, tSerNum, tTrapText}
	STATUS	current
	DESCRIPTION	"Event: Manual Start"
::= { notifications 1073742073 }

tTestStart	NOTIFICATION-TYPE
	OBJECTS	{tControllerName, tSerNum, tTrapText}
	STATUS	current
	DESCRIPTION	"Event: Test Start"
::= { notifications 1073742074 }

tOtherStop	NOTIFICATION-TYPE
	OBJECTS	{tControllerName, tSerNum, tTrapText}
	STATUS	current
	DESCRIPTION	"Event: Other Stop"
::= { notifications 1073742075 }

tManualStop	NOTIFICATION-TYPE
	OBJECTS	{tControllerName, tSerNum, tTrapText}
	STATUS	current
	DESCRIPTION	"Event: Manual Stop"
::= { notifications 1073742076 }

tAMFStop	NOTIFICATION-TYPE
	OBJECTS	{tControllerName, tSerNum, tTrapText}
	STATUS	current
	DESCRIPTION	"Event: AMF Stop"
::= { notifications 1073742077 }

tRemoteStop	NOTIFICATION-TYPE
	OBJECTS	{tControllerName, tSerNum, tTrapText}
	STATUS	current
	DESCRIPTION	"Event: Remote Stop"
::= { notifications 1073742078 }

tPeakStop	NOTIFICATION-TYPE
	OBJECTS	{tControllerName, tSerNum, tTrapText}
	STATUS	current
	DESCRIPTION	"Event: Peak Stop"
::= { notifications 1073742079 }

tPMSStop	NOTIFICATION-TYPE
	OBJECTS	{tControllerName, tSerNum, tTrapText}
	STATUS	current
	DESCRIPTION	"Event: PMS Stop"
::= { notifications 1073742080 }

tModbusRemoteStop	NOTIFICATION-TYPE
	OBJECTS	{tControllerName, tSerNum, tTrapText}
	STATUS	current
	DESCRIPTION	"Event: Modbus Remote Stop"
::= { notifications 1073742718 }

tDCBusDeenergized	NOTIFICATION-TYPE
	OBJECTS	{tControllerName, tSerNum, tTrapText}
	STATUS	current
	DESCRIPTION	"Event: DC Bus Deenergized"
::= { notifications 1073742801 }

tBCBOpened	NOTIFICATION-TYPE
	OBJECTS	{tControllerName, tSerNum, tTrapText}
	STATUS	current
	DESCRIPTION	"Event: BCB Opened"
::= { notifications 1073742083 }

tBCBOpenedExternally	NOTIFICATION-TYPE
	OBJECTS	{tControllerName, tSerNum, tTrapText}
	STATUS	current
	DESCRIPTION	"Event: BCB Opened Externally"
::= { notifications 1073742462 }

tBCBClosed	NOTIFICATION-TYPE
	OBJECTS	{tControllerName, tSerNum, tTrapText}
	STATUS	current
	DESCRIPTION	"Event: BCB Closed"
::= { notifications 1073742084 }

tBCBClosedExternally	NOTIFICATION-TYPE
	OBJECTS	{tControllerName, tSerNum, tTrapText}
	STATUS	current
	DESCRIPTION	"Event: BCB Closed Externally"
::= { notifications 1073742463 }

tMCBOpened	NOTIFICATION-TYPE
	OBJECTS	{tControllerName, tSerNum, tTrapText}
	STATUS	current
	DESCRIPTION	"Event: MCB Opened"
::= { notifications 1073742085 }

tMCBOpenedExternally	NOTIFICATION-TYPE
	OBJECTS	{tControllerName, tSerNum, tTrapText}
	STATUS	current
	DESCRIPTION	"Event: MCB Opened Externally"
::= { notifications 1073742086 }

tMCBClosed	NOTIFICATION-TYPE
	OBJECTS	{tControllerName, tSerNum, tTrapText}
	STATUS	current
	DESCRIPTION	"Event: MCB Closed"
::= { notifications 1073742087 }

tMCBClosedExternally	NOTIFICATION-TYPE
	OBJECTS	{tControllerName, tSerNum, tTrapText}
	STATUS	current
	DESCRIPTION	"Event: MCB Closed Externally"
::= { notifications 1073742464 }

tSyncStarted	NOTIFICATION-TYPE
	OBJECTS	{tControllerName, tSerNum, tTrapText}
	STATUS	current
	DESCRIPTION	"Event: SyncStarted"
::= { notifications 1073742088 }

tRevSyncStarted	NOTIFICATION-TYPE
	OBJECTS	{tControllerName, tSerNum, tTrapText}
	STATUS	current
	DESCRIPTION	"Event: RevSyncStarted"
::= { notifications 1073742089 }

tReady	NOTIFICATION-TYPE
	OBJECTS	{tControllerName, tSerNum, tTrapText}
	STATUS	current
	DESCRIPTION	"Event: Ready"
::= { notifications 1073742090 }

tEnergized	NOTIFICATION-TYPE
	OBJECTS	{tControllerName, tSerNum, tTrapText}
	STATUS	current
	DESCRIPTION	"Event: Energized"
::= { notifications 1073742092 }

tSoftLoad	NOTIFICATION-TYPE
	OBJECTS	{tControllerName, tSerNum, tTrapText}
	STATUS	current
	DESCRIPTION	"Event: Soft Load"
::= { notifications 1073742094 }

tLoaded	NOTIFICATION-TYPE
	OBJECTS	{tControllerName, tSerNum, tTrapText}
	STATUS	current
	DESCRIPTION	"Event: Loaded"
::= { notifications 1073742095 }

tSoftUnload	NOTIFICATION-TYPE
	OBJECTS	{tControllerName, tSerNum, tTrapText}
	STATUS	current
	DESCRIPTION	"Event: Soft Unload"
::= { notifications 1073742096 }

tEmergMAN	NOTIFICATION-TYPE
	OBJECTS	{tControllerName, tSerNum, tTrapText}
	STATUS	current
	DESCRIPTION	"Event: Emerg MAN"
::= { notifications 1073742098 }

tNotReady	NOTIFICATION-TYPE
	OBJECTS	{tControllerName, tSerNum, tTrapText}
	STATUS	current
	DESCRIPTION	"Event: Not Ready"
::= { notifications 1073742099 }

tTestOnLoad	NOTIFICATION-TYPE
	OBJECTS	{tControllerName, tSerNum, tTrapText}
	STATUS	current
	DESCRIPTION	"Event: Test On Load"
::= { notifications 1073742102 }

tLoadShed	NOTIFICATION-TYPE
	OBJECTS	{tControllerName, tSerNum, tTrapText}
	STATUS	current
	DESCRIPTION	"Event: Load Shed"
::= { notifications 1073742302 }

tLoadReconnect	NOTIFICATION-TYPE
	OBJECTS	{tControllerName, tSerNum, tTrapText}
	STATUS	current
	DESCRIPTION	"Event: Load Reconnect"
::= { notifications 1073742303 }

tFence1Alarm	NOTIFICATION-TYPE
	OBJECTS	{tControllerName, tSerNum, tTrapText}
	STATUS	current
	DESCRIPTION	"Event: Fence 1 Alarm"
::= { notifications 1073742119 }

tFence2Alarm	NOTIFICATION-TYPE
	OBJECTS	{tControllerName, tSerNum, tTrapText}
	STATUS	current
	DESCRIPTION	"Event: Fence 2 Alarm"
::= { notifications 1073742120 }

tOtherCBTrip	NOTIFICATION-TYPE
	OBJECTS	{tControllerName, tSerNum, tTrapText}
	STATUS	current
	DESCRIPTION	"Event: Other CB Trip"
::= { notifications 1073742227 }

tEmergencyDroopInactive	NOTIFICATION-TYPE
	OBJECTS	{tControllerName, tSerNum, tTrapText}
	STATUS	current
	DESCRIPTION	"Event: Emergency Droop Inactive"
::= { notifications 1073742230 }

tProtectionForceDisable1Active	NOTIFICATION-TYPE
	OBJECTS	{tControllerName, tSerNum, tTrapText}
	STATUS	current
	DESCRIPTION	"Event: Protection Force Disable 1 active"
::= { notifications 1073742306 }

tProtectionForceDisable1Inactive	NOTIFICATION-TYPE
	OBJECTS	{tControllerName, tSerNum, tTrapText}
	STATUS	current
	DESCRIPTION	"Event: Protection Force Disable 1 inactive"
::= { notifications 1073742307 }

tProtectionForceDisable2Active	NOTIFICATION-TYPE
	OBJECTS	{tControllerName, tSerNum, tTrapText}
	STATUS	current
	DESCRIPTION	"Event: Protection Force Disable 2 active"
::= { notifications 1073742465 }

tProtectionForceDisable2Inactive	NOTIFICATION-TYPE
	OBJECTS	{tControllerName, tSerNum, tTrapText}
	STATUS	current
	DESCRIPTION	"Event: Protection Force Disable 2 inactive"
::= { notifications 1073742466 }

tProtectionForceDisable3Active	NOTIFICATION-TYPE
	OBJECTS	{tControllerName, tSerNum, tTrapText}
	STATUS	current
	DESCRIPTION	"Event: Protection Force Disable 3 active"
::= { notifications 1073742467 }

tProtectionForceDisable3Inactive	NOTIFICATION-TYPE
	OBJECTS	{tControllerName, tSerNum, tTrapText}
	STATUS	current
	DESCRIPTION	"Event: Protection Force Disable 3 inactive"
::= { notifications 1073742468 }

tProtectionForceDisable4Active	NOTIFICATION-TYPE
	OBJECTS	{tControllerName, tSerNum, tTrapText}
	STATUS	current
	DESCRIPTION	"Event: Protection Force Disable 4 active"
::= { notifications 1073742469 }

tProtectionForceDisable4Inactive	NOTIFICATION-TYPE
	OBJECTS	{tControllerName, tSerNum, tTrapText}
	STATUS	current
	DESCRIPTION	"Event: Protection Force Disable 4 inactive"
::= { notifications 1073742470 }

tMissingSWKey	NOTIFICATION-TYPE
	OBJECTS	{tControllerName, tSerNum, tTrapText}
	STATUS	current
	DESCRIPTION	"Event: Missing SW Key"
::= { notifications 1073742761 }

tUserLogin	NOTIFICATION-TYPE
	OBJECTS	{tControllerName, tSerNum, tTrapText}
	STATUS	current
	DESCRIPTION	"Event: User Login"
::= { notifications 1073742499 }

tUserLogout	NOTIFICATION-TYPE
	OBJECTS	{tControllerName, tSerNum, tTrapText}
	STATUS	current
	DESCRIPTION	"Event: User Logout"
::= { notifications 1073742500 }

tMaintenanceTimer1Reset	NOTIFICATION-TYPE
	OBJECTS	{tControllerName, tSerNum, tTrapText}
	STATUS	current
	DESCRIPTION	"Event: Maintenance Timer 1 Reset"
::= { notifications 1073742594 }

tMaintenanceTimer2Reset	NOTIFICATION-TYPE
	OBJECTS	{tControllerName, tSerNum, tTrapText}
	STATUS	current
	DESCRIPTION	"Event: Maintenance Timer 2 Reset"
::= { notifications 1073742595 }

tMaintenanceTimer3Reset	NOTIFICATION-TYPE
	OBJECTS	{tControllerName, tSerNum, tTrapText}
	STATUS	current
	DESCRIPTION	"Event: Maintenance Timer 3 Reset"
::= { notifications 1073742596 }

tMaintenanceTimer4Reset	NOTIFICATION-TYPE
	OBJECTS	{tControllerName, tSerNum, tTrapText}
	STATUS	current
	DESCRIPTION	"Event: Maintenance Timer 4 Reset"
::= { notifications 1073742724 }

tPVCBOpened	NOTIFICATION-TYPE
	OBJECTS	{tControllerName, tSerNum, tTrapText}
	STATUS	current
	DESCRIPTION	"Event: PVCB Opened"
::= { notifications 1073742762 }

tPVCBClosed	NOTIFICATION-TYPE
	OBJECTS	{tControllerName, tSerNum, tTrapText}
	STATUS	current
	DESCRIPTION	"Event: PVCB Closed"
::= { notifications 1073742763 }




--******************************************************************--

END
